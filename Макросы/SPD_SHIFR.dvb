Attribute VB_Name = "ClassINI"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
 
Private strInI As String
 
'// Win API Declares
Private Declare Function WritePrivateProfileString _
  Lib "kernel32" Alias "WritePrivateProfileStringA" _
 (ByVal lpApplicationName As String, _
  ByVal lpKeyName As Any, _
  ByVal lpString As Any, _
  ByVal lpFileName As String) As Long
 
Private Declare Function GetPrivateProfileString _
  Lib "kernel32" Alias "GetPrivateProfileStringA" _
 (ByVal lpApplicationName As String, _
  ByVal lpKeyName As Any, _
  ByVal lpDefault As String, _
  ByVal lpReturnedString As String, _
  ByVal nSize As Long, _
  ByVal lpFileName As String) As Long
 
Private Function MakePath(ByVal strFileName As String, _
  ByVal strPath As String) As String
 
 '// Makes an INI file: Guarantees a sub dir
 Do While VBA.Right$(strPath, 1) = "\"
   strPath = VBA.Left$(strPath, Len(strPath) - 1)
 Loop
 
 Do While VBA.Left$(strFileName, 1) = "\"
   strFileName = VBA.Mid$(strFileName, 2)
 Loop
 
 '// Return the path
 MakePath = strPath & "\" & strFileName
End Function
 
Public Sub CreateIni(strFileName As String, strPath As String)
 '// Make a new ini file
 strInI = MakePath(strFileName, strPath)
End Sub
 
Public Sub WriteFile(strSection As String, _
 strKey As String, _
 strValue As String)
 
 '// Write to strINI
 WritePrivateProfileString strSection, _
   strKey, strValue, strInI
End Sub
 
Public Function GetFile(strSection As String, _
  strKey As String) As String
 
  Dim strTmp As String
  Dim lngRet As String
 
  strTmp = VBA.String$(100, 0)
  lngRet = GetPrivateProfileString(strSection, _
    strKey, "", strTmp, _
    Len(strTmp), strInI)
 
  GetFile = StrZ(strTmp)
 
End Function
 
Public Property Let INIFile(ByVal New_IniPath As String)
   'Устанавливаем путь к файлу ini
   strInI = New_IniPath
End Property
Public Property Get INIFile() As String
   INIFile = strInI
End Property
 
 
'v_1.0.0 990630
Private Function StrZ(par As String) As String
Dim nSize As Long, i As Long, Rez As String
   nSize = Len(par)
   i = InStr(1, par, VBA.Chr(0)) - 1
   If i > nSize Then i = nSize
   If i < 0 Then i = nSize
   StrZ = VBA.Mid(par, 1, i)
End Function

Attribute VB_Name = "FormInput"
Attribute VB_Base = "0{BB9821E7-A4AA-4D8D-89F1-7692D90F4F71}{FB64EE05-2F08-4A4F-87D7-C0AFD01AB075}"
Attribute VB_GlobalNameSpace = False
Attribute VB_Creatable = False
Attribute VB_PredeclaredId = True
Attribute VB_Exposed = False
Attribute VB_TemplateDerived = False
Attribute VB_Customizable = False
Option Explicit

Private Sub cmbCancel_Click()
   TextBoxName = ""
   Hide
End Sub

Private Sub cmbOK_Click()
   If TextBoxName = "" Then
      MsgBox "Пустое имя не допускается!", vbCritical, psVBProjectName
      Exit Sub
   End If
   
   Hide
   
End Sub

Private Sub UserForm_Click()

End Sub

Attribute VB_Name = "FormInsStamp1"
Attribute VB_Base = "0{152AAF27-7401-48B4-BD99-E0C08DF06874}{59DE6A22-7AB3-49EE-8BB2-994B14205BBE}"
Attribute VB_GlobalNameSpace = False
Attribute VB_Creatable = False
Attribute VB_PredeclaredId = True
Attribute VB_Exposed = False
Attribute VB_TemplateDerived = False
Attribute VB_Customizable = False
Option Explicit

Private Sub CheckBoxOsnKomplect_Click()
   If CheckBoxOsnKomplect.Value = True Then
      TextBoxShifr = objRecShifr!Шифр & objRecShifr!БС & "-" & objRecShifr!Часть
   Else
      TextBoxShifr = objRecShifr!Шифр & "-" & objRecShifr!Часть
   End If
End Sub

Private Sub cmbExit_Click()
   
   If TextBoxFam5 <> "" Then
      'записываем фамилию пользователя в ини
      Functions.SetUserFamily (TextBoxFam5)
   End If
   
   Hide
End Sub

Private Sub cmbOK_Click()
   'вставить блок штампа
   
   Dim strMacroPath As String
   Dim strStampFullPath  As String
   Dim objBlockStamp As AcadBlockReference
   Dim objLayer As AcadLayer
   Dim varInsPt As Variant
   Dim varAtr As Variant
   Dim dPt(2) As Double
   
   On Error GoTo HasError
   
   'скрываем форму
   Hide
   
   'блок штампа вставлять на слой "РАМКА"
   Set objLayer = Functions.GetLayer("РАМКА")
   objLayer.Lock = False
   objLayer.LayerOn = True
   If ThisDrawing.ActiveLayer.Name <> "РАМКА" Then
      objLayer.Freeze = False
   End If
   
   'получаем полный путь к макросу
   strMacroPath = Functions.GetMacroFolder(psVBProjectName)
   
   'находим файл штампа
   strStampFullPath = strMacroPath & "\Блоки\Штампы.dwg"
   If Dir(strStampFullPath) = "" Then
      MsgBox "Не найден файл со штампами - " & strStampFullPath & vbCrLf & _
            "Выход.", vbCritical, psVBProjectName
      Exit Sub
   End If
   
   'вставляем определение блоков штампов из файла "Штампы.dwg", из корня макроса
'   Set objBlockStamp = ThisDrawing.ModelSpace.InsertBlock(dPt, strStampFullPath, _
'         1, 1, 1, 0)
'   'удаляем блок
'   objBlockStamp.Delete
   RedefineBlock strStampFullPath, "Штамп1"
   
   'запрашивае точку вставки
   varInsPt = ThisDrawing.Utility.GetPoint(, "Точка нижнего правого угла штампа")
   
   'определение текущего пространства
   If ThisDrawing.ActiveSpace = acModelSpace Then
      'вставляем определение блоков штампов из файла "Штампы.dwg", из корня макроса
      Set objBlockStamp = ThisDrawing.ModelSpace.InsertBlock(varInsPt, "Штамп1", _
            TextBoxM, TextBoxM, 1, 0)
   Else
      Set objBlockStamp = ThisDrawing.PaperSpace.InsertBlock(varInsPt, "Штамп1", _
            1, 1, 1, 0)
   End If
   
   'назначаем слой
   objBlockStamp.layer = "РАМКА"
         
   'заполняем атрибуты
   varAtr = objBlockStamp.GetAttributes
   
   varAtr(0).TextString = TextBoxShifr
   varAtr(1).TextString = TextBoxClient
   varAtr(2).TextString = TextBoxAdress
   varAtr(3).TextString = TextBoxNomerDoma
   varAtr(4).TextString = TextBoxNaimen
   varAtr(5).TextString = TextBoxPost1
   varAtr(6).TextString = TextBoxFam1
   varAtr(7).TextString = TextBoxPost2
   varAtr(8).TextString = TextBoxFam2
   varAtr(9).TextString = TextBoxPost3
   varAtr(10).TextString = TextBoxFam3
   varAtr(11).TextString = TextBoxPost4
   varAtr(12).TextString = TextBoxFam4
   varAtr(13).TextString = TextBoxPost5
   varAtr(14).TextString = TextBoxFam5
   If Len(TextBoxFam5) > 10 Then
      varAtr(14).ScaleFactor = 0.8
   End If
   varAtr(15).TextString = TextBoxPost6
   varAtr(16).TextString = TextBoxFam6
   If Len(TextBoxFam6) > 10 Then
      varAtr(16).ScaleFactor = 0.8
   End If
   varAtr(19).TextString = TextBoxStage
   
   FormInsStamp1.Show

Exit Sub

HasError:
   Select Case Err.Number
      Case "-2145386476" 'Ключ не найден
         Resume Next
      Case Else
         MsgBox Err.Description, vbCritical, psVBProjectName
         Exit Sub
   End Select
   
End Sub

Private Sub cmbRefresh_Click()
   'обновить данные всех блоков штампов на чертеже
   
   On Error GoTo HasError
   
   Dim colStampBlocks As New Collection
   Dim colStampIzdBlocks As New Collection
   Dim colStampBlocksDoZam As New Collection
   Dim colStampIzdBlocksDoZam As New Collection
   Dim colStampIzdNextBlocks As New Collection
   Dim objBlockStamp As AcadBlockReference
   Dim varAtr As Variant
   Dim objAtrStamp As AcadAttributeReference
   Dim i As Integer
   Dim strStampFullPath As String
   Dim strMacroPath As String
   
   Hide
   
   'получаем полный путь к макросу
   strMacroPath = Functions.GetMacroFolder(psVBProjectName)
   
   'находим файл штампа
   strStampFullPath = strMacroPath & "\Блоки\Штампы.dwg"
   If Dir(strStampFullPath) = "" Then
      MsgBox "Не найден файл со штампами - " & strStampFullPath & vbCrLf & _
            "Выход.", vbCritical, psVBProjectName
      Exit Sub
   End If
   
   'выбираем блоки штампов "Штамп1"
   Set colStampBlocksDoZam = Functions.GetColBlockName("Штамп1")
   'Set colStampIzdBlocksDoZam = Functions.GetColBlockName("ШтампИзд")
   'Set colStampIzdNextBlocks = Functions.GetColBlockName("ШтампИздСлед")
'   If colStampBlocks Is Nothing Then
'      MsgBox "В чертеже нет блоков основного штампа."
'      Exit Sub
'   End If

   '13/01/2012. Изменения
   'Нужно заменит блоки. Чтобы привести в соответствие геометрию и атрибуты.
   'При этом нужно максимально сохранить значения атрибутов
   'ГИП - 1 строка, Нач.АКМ - 2, и т.д.
   
   'переопределение блоков штампов (Штамп1 и ШтампИзд)
   Functions.RedefineBlock strStampFullPath, "Штамп1"
   'Functions.RedefineBlock strStampFullPath, "ШтампИзд"
    
   Dim blRef As AcadBlockReference
   For Each blRef In colStampBlocksDoZam
      Set blRef = Functions.ZamenaBlockaStampa(blRef)
      colStampBlocks.Add blRef
   Next
'   For Each blRef In colStampIzdBlocksDoZam
'      Set blRef = Functions.ZamenaBlockaStampa(blRef)
'      colStampIzdBlocks.Add blRef
'   Next
   
   If colStampBlocks.count <> 0 Then
      'записываем атрибуты
      For Each objBlockStamp In colStampBlocks
         'получаем массив атрибутов
         varAtr = objBlockStamp.GetAttributes
         'заполнняем атрибуты
         varAtr(0).TextString = TextBoxShifr ' Шифр
         varAtr(1).TextString = TextBoxClient ' Заказчик
         varAtr(2).TextString = TextBoxAdress ' Адрес
         varAtr(3).TextString = TextBoxNomerDoma ' Номер_дома
         'varAtr(4).TextString - наименовыание чертежа
         varAtr(5).TextString = TextBoxPost1
         varAtr(6).TextString = TextBoxFam1 ' ФАМГИП
         varAtr(7).TextString = TextBoxPost2
         varAtr(8).TextString = TextBoxFam2
         varAtr(9).TextString = TextBoxPost3
         varAtr(10).TextString = TextBoxFam3
         varAtr(11).TextString = TextBoxPost4 ' ГЛСПЕЦ
         varAtr(12).TextString = TextBoxFam4 ' ФАМГЛСПЕЦ
         varAtr(13).TextString = TextBoxPost5
         If Len(TextBoxFam5) > 10 Then
            varAtr(14).ScaleFactor = 0.8
         End If
         varAtr(14).TextString = TextBoxFam5
         
         varAtr(15).TextString = TextBoxPost6
         If Len(TextBoxFam6) > 10 Then
            varAtr(16).ScaleFactor = 0.8
         End If
         varAtr(16).TextString = TextBoxFam6
         varAtr(19).TextString = TextBoxStage
         
         ' varAtr(15) - ИНЖ2
         ' varAtr(16) - ФАМИНЖ2
         ' varAtr(17) - ЛИСТ
         ' varAtr(18) - ЛИСТОВ
         
      Next
   End If
   If colStampIzdBlocks.count <> 0 Then
      'записываем атрибуты
      For Each objBlockStamp In colStampIzdBlocks
         'получаем массив атрибутов
         varAtr = objBlockStamp.GetAttributes
         'заполнняем атрибуты
         varAtr(0).TextString = TextBoxShifr ' Шифр
         varAtr(2).TextString = TextBoxPost3 ' НАЧСПД
         varAtr(3).TextString = TextBoxFam3 ' ФАМНАЧСПД
         varAtr(4).TextString = TextBoxPost4 ' ГЛСПЕЦ
         varAtr(5).TextString = TextBoxFam4 ' ФАМГЛСПЕЦ
         varAtr(6).TextString = TextBoxPost5
         If Len(TextBoxFam5) > 10 Then
            varAtr(7).ScaleFactor = 0.8
         End If
         varAtr(7).TextString = TextBoxFam5
         
         varAtr(8).TextString = TextBoxPost6
         If Len(TextBoxFam6) > 10 Then
            varAtr(9).ScaleFactor = 0.8
         End If
         varAtr(9).TextString = TextBoxFam6
         varAtr(10).TextString = TextBoxStage
      Next
   End If
   If colStampIzdNextBlocks.count <> 0 Then
      'записываем атрибуты
      For Each objBlockStamp In colStampIzdNextBlocks
         'получаем массив атрибутов
         varAtr = objBlockStamp.GetAttributes
         'заполнняем атрибуты
         varAtr(0).TextString = TextBoxShifr
      Next
   End If
   
   Show
         
Exit Sub

HasError:
   Select Case Err.Number
      Case Else
         MsgBox "Форма FormInsStamp1, процедура cmbRefresh_Click" & vbCrLf & _
            Err.Description, vbCritical, psVBProjectName
            Show
         Exit Sub
   End Select
   
End Sub

'Private Sub cmbShifrs_Click()
'   'вывод формы каталога шфров
'   'редактирование шифра чертежа
'   'возвращение назад
'
'   On Error GoTo HasError
'
'   FormShifr.Show
'
'   'после возвращения из формы
'   'считываем поля шифра
'   TextBoxShifr = FormShifr.TextBoxShifr
'   TextBoxClient = FormShifr.TextBoxClient
'   TextBoxAdress = FormShifr.TextBoxAdress
'   TextBoxNomerDoma = FormShifr.TextBoxObjectName
'   TextBoxFamGIP = Functions.GetFamilWithoutInitial(FormShifr.TextBoxGIP)
'   'должност начальника
'   TextBoxSPD = "Нач.СПД"
'   TextBoxAKM = "Нач.АКМ"
'   'фамилия начальника
'   TextBoxFamSPD = Functions.GetFamilWithoutInitial(FormShifr.TextBoxSPD)
'   TextBoxFamAKM = Functions.GetFamilWithoutInitial(FormShifr.TextBoxAKM)
'   'фамилия гд.спец.
'   TextBoxFamGlSpec = Functions.GetFamilWithoutInitial(FormShifr.TextBoxGlSpec)
'
'   'записываем строки по умолчанию
'   'должность ГИП
'   TextBoxGIP = "ГИП"
'   'должност гл.спец
'   TextBoxGlSpec = "Гл.спец."
'
'Exit Sub
'HasError:
'   MsgBox Err.Description, vbCritical, psVBProjectName
'
'End Sub

Private Sub cmbStampIzd_Click()
   
   Hide
   FormInsStampIzd.Show
   
End Sub

Private Sub Label11_Click()

End Sub

Private Sub TextBoxM_Change()
   
   If IsNumeric(TextBoxM.Text) = False Then
      MsgBox "Введите число, для масштаба штампа", vbInformation, psVBProjectName
      TextBoxM = 100
      Exit Sub
   End If
   
End Sub

Private Sub UserForm_Activate()
   
   Dim strDrawFullName As String
   
   strDrawFullName = ThisDrawing.FullName
   If strDrawFullName = "" Then
      strDrawFullName = ThisDrawing.Name & " (не сохранен на диске)"
   End If
   Label1DrawFullNae = strDrawFullName
   
   If objRecShifr.State = adStateClosed Then
      'скрываем чекбокс
      CheckBoxOsnKomplect.Visible = False
   Else
      If objRecShifr!БС = "" Then
         CheckBoxOsnKomplect.Visible = False
      Else
         CheckBoxOsnKomplect.Visible = True
         CheckBoxOsnKomplect.Value = False
      End If
   End If
   
End Sub

Attribute VB_Name = "FormInsStampIzd"
Attribute VB_Base = "0{2E4A1273-643B-4EA6-A0DE-99935FE7AE57}{6712B8A9-04F4-4D22-953F-C55CBA1945CF}"
Attribute VB_GlobalNameSpace = False
Attribute VB_Creatable = False
Attribute VB_PredeclaredId = True
Attribute VB_Exposed = False
Attribute VB_TemplateDerived = False
Attribute VB_Customizable = False
Option Explicit

Private Sub cmbExit_Click()
   
   If TextBoxFam5 <> "" Then
      'записываем фамилию пользователя в ини
      Functions.SetUserFamily (TextBoxFam5)
   End If
   
   Hide
End Sub

Private Sub cmbOK_Click()
   'вставить блок штампа
   
   Dim strMacroPath As String
   Dim strStampFullPath  As String
   Dim objBlockStamp As AcadBlockReference
   Dim objLayer As AcadLayer
   Dim varInsPt As Variant
   Dim varAtr As Variant
   Dim dPt(2) As Double
   
   On Error GoTo HasError
   
   'скрываем форму
   Hide
   
   'блок штампа вставлять на слой "РАМКА"
   Set objLayer = Functions.GetLayer("РАМКА")
   objLayer.Lock = False
   objLayer.LayerOn = True
   If ThisDrawing.ActiveLayer.Name <> "РАМКА" Then
      objLayer.Freeze = False
   End If
   
   'получаем полный путь к макросу
   strMacroPath = Functions.GetMacroFolder(psVBProjectName)
   
   'находим файл штампа
   strStampFullPath = strMacroPath & "\Блоки\Штампы.dwg"
   If Dir(strStampFullPath) = "" Then
      MsgBox "Не найдем файл с блоками штампов тут - " & strStampFullPath & vbCrLf & _
            "Выход.", vbCritical, psVBProjectName
      Exit Sub
   End If
   
   'вставляем определение блоков штампов из файла "Штампы.dwg", из корня макроса
   If Functions.AddBlocksFromDWG(strStampFullPath) = False Then
      'не удалось внедрить блоки штампов
   End If
   
   'запрашивае точку вставки
   varInsPt = ThisDrawing.Utility.GetPoint(, "Точка нижнего правого угла штампа")
   
   'определение текущего пространства
   If ThisDrawing.ActiveSpace = acModelSpace Then
      'вставляем определение блоков штампов из файла "Штампы.dwg", из корня макроса
      Set objBlockStamp = ThisDrawing.ModelSpace.InsertBlock(varInsPt, "ШтампИзд", _
            TextBoxM, TextBoxM, 1, 0)
   Else
      Set objBlockStamp = ThisDrawing.PaperSpace.InsertBlock(varInsPt, "ШтампИзд", _
            1, 1, 1, 0)
   End If
        
   'назначаем слой
   objBlockStamp.layer = "РАМКА"
         
   'заполняем атрибуты
   varAtr = objBlockStamp.GetAttributes
   
   varAtr(0).TextString = TextBoxShifr
   varAtr(1).TextString = TextBoxNaimen
   varAtr(2).TextString = TextBoxPost3
   varAtr(3).TextString = TextBoxFam3
   varAtr(4).TextString = TextBoxPost4
   varAtr(5).TextString = TextBoxFam4
   varAtr(6).TextString = TextBoxPost5
   varAtr(7).TextString = TextBoxFam5
   varAtr(8).TextString = TextBoxPost6
   varAtr(9).TextString = TextBoxFam6
   'varAtr (10) - должность 5 строка в штампе (не используется)
   'varAtr (11)- фамилия 5 строка в штампе (не используется)
   varAtr(12).TextString = TextBoxList
   varAtr(13).TextString = TextBoxListov
   varAtr(14).TextString = TextBoxStage
   
   FormInsStampIzd.Show
   
Exit Sub

HasError:
   Select Case Err.Number
      Case "-2145386476" 'Ключ не найден
         MsgBox "FormInsStampIzd, cmbOK" & vbCrLf & _
               Err.Description, vbCritical, psVBProjectName
      Case Else
         MsgBox "FormInsStampIzd, cmbOK" & vbCrLf & _
               Err.Description, vbCritical, psVBProjectName
   End Select
   
End Sub

Private Sub cmbStamp1_Click()
   
      Hide
      FormInsStamp1.Show
   
End Sub

Private Sub cmbStapmIzdNext_Click()
   
   Hide
   FormInsStampIzdNext.Show
   
End Sub

Private Sub UserForm_Activate()
   'считываем инфе из FormInsStamp1
   
   Label1DrawFullNae = FormInsStamp1.Label1DrawFullNae
   TextBoxShifr = FormInsStamp1.TextBoxShifr & ".И-"
   TextBoxPost3 = FormInsStamp1.TextBoxPost3
   TextBoxFam3 = FormInsStamp1.TextBoxFam3
   TextBoxPost4 = FormInsStamp1.TextBoxPost4
   TextBoxFam4 = FormInsStamp1.TextBoxFam4
   TextBoxPost5 = FormInsStamp1.TextBoxPost5
   TextBoxFam5 = FormInsStamp1.TextBoxFam5
   TextBoxPost6 = FormInsStamp1.TextBoxPost6
   TextBoxFam6 = FormInsStamp1.TextBoxFam6
   TextBoxStage = FormInsStamp1.TextBoxStage
   
End Sub

Private Sub TextBoxM_Change()
   
   If IsNumeric(TextBoxM.Text) = False Then
      MsgBox "Введите число, для масштаба штампа", vbCritical, psVBProjectName
      TextBoxM = 100
      Exit Sub
   End If
   
End Sub

Attribute VB_Name = "FormInsStampIzdNext"
Attribute VB_Base = "0{36D0CAB2-5984-4FAE-8FA8-D62B6D4E2DD8}{0FB32704-56AE-4377-BBB3-B644FC61D595}"
Attribute VB_GlobalNameSpace = False
Attribute VB_Creatable = False
Attribute VB_PredeclaredId = True
Attribute VB_Exposed = False
Attribute VB_TemplateDerived = False
Attribute VB_Customizable = False
Option Explicit

Private Sub cmbExit_Click()
   Hide
End Sub

Private Sub cmbOK_Click()
   'вставить блок штампа
   
   Dim strMacroPath As String
   Dim strStampFullPath  As String
   Dim objBlockStamp As AcadBlockReference
   Dim objLayer As AcadLayer
   Dim varInsPt As Variant
   Dim varAtr As Variant
   Dim dPt(2) As Double
   
   On Error GoTo HasError
   
   'скрываем форму
   Hide
   
   'блок штампа вставлять на слой "РАМКА"
   Set objLayer = ThisDrawing.Layers.Item("РАМКА")
   If objLayer Is Nothing Then
      Set objLayer = ThisDrawing.Layers.Add("РАМКА")
   End If
   objLayer.Lock = False
   objLayer.LayerOn = True
   If ThisDrawing.ActiveLayer.Name <> "РАМКА" Then
      objLayer.Freeze = False
   End If
   
   'получаем полный путь к макросу
   strMacroPath = Functions.GetMacroFolder(psVBProjectName)
   
   'находим файл штампа
   strStampFullPath = strMacroPath & "\Блоки\Штампы.dwg"
   If Dir(strStampFullPath) = "" Then
      MsgBox "Не найдем файл с блоками штампов тут - " & strStampFullPath & vbCrLf & _
            "Выход.", vbCritical, psVBProjectName
      Exit Sub
   End If
   
   'вставляем определение блоков штампов из файла "Штампы.dwg", из корня макроса
   If Functions.AddBlocksFromDWG(strStampFullPath) = False Then
      'не удалось внедрить блоки штампов
   End If
   
   'запрашивае точку вставки
   varInsPt = ThisDrawing.Utility.GetPoint(, "Точка нижнего правого угла штампа")
   
   'определение текущего пространства
   If ThisDrawing.ActiveSpace = acModelSpace Then
      'вставляем определение блоков штампов из файла "Штампы.dwg", из корня макроса
      Set objBlockStamp = ThisDrawing.ModelSpace.InsertBlock(varInsPt, "ШтампИздСлед", _
            TextBoxM, TextBoxM, 1, 0)
   Else
      Set objBlockStamp = ThisDrawing.PaperSpace.InsertBlock(varInsPt, "ШтампИздСлед", _
            1, 1, 1, 0)
   End If
   
   'назначаем слой
   objBlockStamp.layer = "РАМКА"
         
   'заполняем атрибуты
   varAtr = objBlockStamp.GetAttributes
   
   varAtr(0).TextString = TextBoxShifr
   varAtr(1).TextString = TextBoxList
   
   FormInsStampIzdNext.Show

Exit Sub

HasError:
   Select Case Err.Number
      Case "-2145386476" 'Ключ не найден
         Resume Next
      Case Else
         MsgBox "FormInsStampIzd, cmbOK" & vbCrLf & _
               Err.Description, vbCritical, psVBProjectName
   End Select
   
End Sub

Private Sub cmbStampIzd_Click()
   Hide
   FormInsStampIzd.Show
End Sub

Private Sub UserForm_Activate()
   
   TextBoxShifr = FormInsStampIzd.TextBoxShifr
   
End Sub

Attribute VB_Name = "FormOptions"
Attribute VB_Base = "0{B0971DD7-8555-4D70-B231-60514F214BC1}{41F2E5F0-AA16-4AA7-84FE-D6649F88365B}"
Attribute VB_GlobalNameSpace = False
Attribute VB_Creatable = False
Attribute VB_PredeclaredId = True
Attribute VB_Exposed = False
Attribute VB_TemplateDerived = False
Attribute VB_Customizable = False
Option Explicit

'настройка параметров работы проги

'слои для вставки штампа и схемы

Private Sub UserForm_Click()

End Sub

Attribute VB_Name = "FormShifr"
Attribute VB_Base = "0{5B3E2132-2F94-4D83-A452-02E18DA6FAF3}{E0569C26-E150-4E14-AE4E-1F9FE1C3B021}"
Attribute VB_GlobalNameSpace = False
Attribute VB_Creatable = False
Attribute VB_PredeclaredId = True
Attribute VB_Exposed = False
Attribute VB_TemplateDerived = False
Attribute VB_Customizable = False
Option Explicit

Private Sub CheckBoxOsnKomplect_Click()
   
   Dim objListItem As ListItem
   Set objListItem = ListViewShifr.SelectedItem
   If objListItem Is Nothing Then
      MsgBox "Не выбран шифр в таблице!", vbCritical, psVBProjectName
      Exit Sub
   End If
   
   If CheckBoxOsnKomplect.Value = True Then
      TextBoxShifr = objListItem & objListItem.SubItems(1) & "-" & objListItem.SubItems(2)
   Else
      TextBoxShifr = objListItem & "-" & objListItem.SubItems(2)
   End If
End Sub

Private Sub cmbInsStamp_Click()
   'процедура вставки блока штампа в текущий чертеж
   
   Hide
   InsStamp
   FormShifr.Show vbModeless
   
End Sub

Private Sub cmbReload_Click()
   'обновить данные из базы
   Dim objListItem As ListItem
   Dim strSelShifr As String
   
   Set objListItem = ListViewShifr.SelectedItem
   If Not objListItem Is Nothing Then
      strSelShifr = objListItem
   End If
   
   'обновление данных формы
   UserForm_Activate
   
   If strSelShifr <> "" Then
      'находим шифр который был выделен до обновления
      Set objListItem = ListViewShifr.FindItem(strSelShifr)
      If Not objListItem Is Nothing Then
         objListItem.Selected = True
         ListViewShifr_ItemClick objListItem
      End If
   End If
   
End Sub

Private Sub ComboBoxFilterSer_Change()
   'фильтр по серии
   Dim objListItem As ListItem
   Dim strSQL As String
   
   On Error GoTo HasError
   
   If ComboBoxFilterSer.ListIndex = -1 Then Exit Sub
   
   If ComboBoxFilterSer = "Все" Then
      'заполняем листвиевер всеми шифрами
'      objRecSet.Filter = adFilterNone
      UserForm_Activate
      Exit Sub
   Else
      'запрос шифров
      If objRecSet.State = adStateOpen Then objRecSet.Close
      objRecSet.Filter = adFilterNone
      strSQL = "SELECT * FROM Шифры ORDER BY Шифры.Дата_создания"
      'strSQL = "SELECT Шифры.Шифр, Шифры.БС, Шифры.Часть, Шифры.Серия, Шифры.Адрес, Шифры.Наимен_объекта, Шифры.ГИП, Шифры.Заказчик, Шифры.Нач_отд,Шифры.Отд,  Шифры.Гл_спец " & _
            "FROM Серии INNER JOIN (Нач_отд INNER JOIN (Заказчики INNER JOIN (Гл_спецы INNER JOIN (ГИПЫ INNER JOIN Шифры ON ГИПЫ.Фамилия = Шифры.ГИП) ON Гл_спецы.Фамилия = Шифры.Гл_спец) ON Заказчики.Название = Шифры.Заказчик) ON Нач_отд.Фамилия = Шифры.Нач_отд) ON Серии.Имя = Шифры.Серия " & _
            "ORDER BY Шифры.Шифр"
      objRecSet.Open Source:=strSQL, ActiveConnection:=objConect, _
                     CursorType:=adOpenKeyset, LockType:=adLockOptimistic, Options:=adCmdText
      If objRecSet.EOF And objRecSet.BOF Then
         MsgBox "Нет шифров в катологе!", vbExclamation, psVBProjectName
         Exit Sub
      End If
   
      'фильт
      objRecSet.MoveFirst
      objRecSet.Filter = "Серия = '" & ComboBoxFilterSer & "'"
      If objRecSet.EOF And objRecSet.BOF Then
         'нет записей, очищаем листвиевер
         ListViewShifr.ListItems.Clear
         Exit Sub
      End If
   End If
   
   'заполняем листвиевер шифрами с зоданной серией
   ListViewShifr.ListItems.Clear
   
   objRecSet.MoveFirst
   Do Until objRecSet.EOF
      'добавление записи в листвиев
      Set objListItem = ListViewShifr.ListItems.Add(, , objRecSet!Шифр)
      objListItem.SubItems(1) = objRecSet!БС
      objListItem.SubItems(2) = objRecSet!Часть
      objListItem.SubItems(3) = objRecSet!Серия
      objListItem.SubItems(4) = objRecSet!Наимен_объекта
      objListItem.SubItems(5) = objRecSet!Адрес
      objListItem.SubItems(6) = objRecSet!Заказчик
      objListItem.SubItems(7) = objRecSet!Должность1
      objListItem.SubItems(8) = objRecSet!Фамилия1
      objListItem.SubItems(9) = objRecSet!Должность2
      objListItem.SubItems(10) = objRecSet!Фамилия2
      objListItem.SubItems(11) = objRecSet!Должность3
      objListItem.SubItems(12) = objRecSet!Фамилия3
      objListItem.SubItems(13) = objRecSet!Должность4
      objListItem.SubItems(14) = objRecSet!Фамилия4
      objListItem.SubItems(15) = objRecSet!Стадия
      objListItem.SubItems(16) = objRecSet!Дата_создания
      objRecSet.MoveNext
   Loop
   
Exit Sub
HasError:
   If Err.Number = 94 Then Resume Next
   MsgBox Err.Description, vbCritical, psVBProjectName

End Sub

Private Sub CreateTitList_Click()
  'Создание обложки
  'Для выделенного шифра
  
  'форма для задание название альбома
  Set FormTitList.objListItem = ListViewShifr.SelectedItem
  
  If FormTitList.objListItem Is Nothing Then
      MsgBox "Не выбран шифр в таблице!", vbCritical, psVBProjectName
      Exit Sub
   End If
  
  Me.Hide
  
  FormTitList.Show
  
  Me.Show
  
End Sub

Private Sub Frame1_Click()

End Sub

Private Sub Frame2_Click()

End Sub

Private Sub ListViewShifr_DblClick()
   'запись шифра в текущий чертеж
   
   cmbSetShifrToDraw_Click
   
End Sub

Private Sub TextBoxFind_Change()
   'поиск по шифру
   
   'если пустая строка поиска, то выводим все шифры
   If TextBoxFind = "" Then
      If ComboBoxFilterSer.ListIndex = -1 Then
         'заполняем листвиевер всеми шифрами
   '      objRecSet.Filter = adFilterNone
         UserForm_Activate
         Exit Sub
      Else
         ComboBoxFilterSer_Change
         Exit Sub
      End If
   End If
   
   FindShifrsToListViev (TextBoxFind)
   
End Sub

Private Sub UserForm_Initialize()
   'будет ли инициализироваться в случае повторного запуска?
   'стандартный листвиев можно замеить на Microsoft Office Spreadsheet 10
   
   Dim strConect As String
   Dim strMacroFolder As String
   
   On Error GoTo HasError

' ********** Подключение к базе - Connection *****************
   
   If objConect.State = adStateOpen Then
      'подключение уже открыто
      objConect.Close
   End If
   strMacroFolder = Functions.GetMacroFolder(psVBProjectName)
   
   'резервная копия базы
   On Error Resume Next
   FileCopy strMacroFolder & "\Базы\Шифры.mdb", strMacroFolder & "\Базы\Шифры_копия.mdb"
   On Error GoTo HasError
   
   'строка подключения
   strConect = strProvider & _
            "Data Source=" & strMacroFolder & "\Базы\Шифры.mdb"
   'подключение
   objConect.CursorLocation = adUseClient
   objConect.Mode = adModeWrite  'дугие смогут тоже подключатьься
   objConect.Open strConect

   'вставляем столбцы в листвиевер
   ListViewShifr.ColumnHeaders.Add 1, , "Шифр"
   ListViewShifr.ColumnHeaders.Item(1).Width = 60
   ListViewShifr.ColumnHeaders.Add 2, , "(бс)"
   ListViewShifr.ColumnHeaders.Item(2).Width = 30
   ListViewShifr.ColumnHeaders.Add 3, , "Часть"
   ListViewShifr.ColumnHeaders.Item(3).Width = 30
   ListViewShifr.ColumnHeaders.Add 4, , "Серия"
   ListViewShifr.ColumnHeaders.Item(4).Width = 45
   ListViewShifr.ColumnHeaders.Add 5, , "Объект"
   ListViewShifr.ColumnHeaders.Item(5).Width = 75
   ListViewShifr.ColumnHeaders.Add 6, , "Адрес"
   ListViewShifr.ColumnHeaders.Item(6).Width = 50
   ListViewShifr.ColumnHeaders.Add 7, , "Заказчик"
   ListViewShifr.ColumnHeaders.Item(7).Width = 80
   ListViewShifr.ColumnHeaders.Add 8, , "Должность1"
   ListViewShifr.ColumnHeaders.Item(8).Width = 30
   ListViewShifr.ColumnHeaders.Add 9, , "Фамилия1"
   ListViewShifr.ColumnHeaders.Item(9).Width = 65
   ListViewShifr.ColumnHeaders.Add 10, , "Должность2"
   ListViewShifr.ColumnHeaders.Item(10).Width = 60
   ListViewShifr.ColumnHeaders.Add 11, , "Фамилия2"
   ListViewShifr.ColumnHeaders.Item(11).Width = 60
   ListViewShifr.ColumnHeaders.Add 12, , "Должность3"
   ListViewShifr.ColumnHeaders.Item(12).Width = 60
   ListViewShifr.ColumnHeaders.Add 13, , "Фамилия3"
   ListViewShifr.ColumnHeaders.Item(13).Width = 60
   ListViewShifr.ColumnHeaders.Add 14, , "Должность4"
   ListViewShifr.ColumnHeaders.Item(14).Width = 60
   ListViewShifr.ColumnHeaders.Add 15, , "Фамилия4"
   ListViewShifr.ColumnHeaders.Item(15).Width = 60
   ListViewShifr.ColumnHeaders.Add 16, , "Стадия"
   ListViewShifr.ColumnHeaders.Item(16).Width = 40
   ListViewShifr.ColumnHeaders.Add 17, , "Дата создания"
   ListViewShifr.ColumnHeaders.Item(17).Width = 70
   
   ListViewShifr.SortKey = 16
   ListViewShifr.SortOrder = lvwDescending
   
'   bolIzm = False
'   cmbSave.Enabled = False

Exit Sub
HasError:
   MsgBox Err.Description, vbCritical, psVBProjectName
   
End Sub

Private Sub UserForm_Activate()
   Dim strSQL As String
   Dim objListItem As ListItem
   Dim objRec As New ADODB.Recordset
   
   On Error GoTo HasError
   
   'запрос шифров
   If objRecSet.State = adStateOpen Then objRecSet.Close
   objRecSet.Filter = adFilterNone
   strSQL = "Select Шифры.* From Шифры ORDER BY Шифры.Дата_создания"
   objRecSet.Open Source:=strSQL, ActiveConnection:=objConect, _
                  CursorType:=adOpenKeyset, LockType:=adLockOptimistic, Options:=adCmdText
   If objRecSet.EOF And objRecSet.BOF Then
      MsgBox "Нет шифров в катологе!", vbExclamation, psVBProjectName
      Exit Sub
   End If
   
   ListViewShifr.ListItems.Clear
   
   'заполняем листвиевер шифров
   objRecSet.MoveFirst
   Do Until objRecSet.EOF
      'добавление записи в листвиев
      Set objListItem = ListViewShifr.ListItems.Add(, , objRecSet!Шифр)
      objListItem.SubItems(1) = objRecSet!БС
      objListItem.SubItems(2) = objRecSet!Часть
      objListItem.SubItems(3) = objRecSet!Серия
      objListItem.SubItems(4) = objRecSet!Наимен_объекта
      objListItem.SubItems(5) = objRecSet!Адрес
      objListItem.SubItems(6) = objRecSet!Заказчик
      objListItem.SubItems(7) = objRecSet!Должность1
      objListItem.SubItems(8) = objRecSet!Фамилия1
      objListItem.SubItems(9) = objRecSet!Должность2
      objListItem.SubItems(10) = objRecSet!Фамилия2
      objListItem.SubItems(11) = objRecSet!Должность3
      objListItem.SubItems(12) = objRecSet!Фамилия3
      objListItem.SubItems(13) = objRecSet!Должность4
      objListItem.SubItems(14) = objRecSet!Фамилия4
      objListItem.SubItems(15) = objRecSet!Стадия
      objListItem.SubItems(16) = objRecSet!Дата_создания
      objRecSet.MoveNext
   Loop
   
   'заполняем комбобокс серий для фильтра
   ComboBoxFilterSer.Clear
   ComboBoxFilterSer.AddItem "Все"
   strSQL = "SELECT Серия FROM Шифры GROUP BY Серия ORDER BY Серия"
   objRec.Open Source:=strSQL, ActiveConnection:=objConect, _
                  CursorType:=adOpenKeyset, LockType:=adLockOptimistic, Options:=adCmdText
   If objRec.EOF And objRec.BOF Then
      'нет серий
   Else
      objRec.MoveFirst
      Do Until objRec.EOF
         ComboBoxFilterSer.AddItem objRec!Серия
         objRec.MoveNext
      Loop
   End If
'   ComboBoxFilterSer = "Все"

Exit Sub
HasError:
   If Err.Number = 94 Then
      Resume Next
   End If
   MsgBox Err.Description, vbCritical, psVBProjectName
   
End Sub

Private Sub cmbDrawReload_Click()
   'получить инфу текущего чертежа
   'полный путь
   'и шифр из словаря
   
   Dim strShifr As String
   Dim strValue As String
   
   On Error GoTo HasError

   'текущий чертеж
   strValue = ThisDrawing.FullName
   If strValue = "" Then
      strValue = ThisDrawing.Name & " (не сохранен)"
   End If
   TextBoxDrawFullPath = strValue
   'очищаем поле
   TextBoxDrawShifr = ""
   
   'получаем строку шифра чертежа из словаря
   '"SPD"-название словаря, в чертеже
   '"Shifr"-название XRecord записи в словаре
   strShifr = Functions.GetShifrFromDict
      
   'если не пусто, то заполняем данные
   If strShifr = "" Then
      MsgBox "Текущему чертежу шифр не назначен", vbInformation, psVBProjectName
      Exit Sub
   End If
   
   TextBoxDrawShifr = strShifr
   
Exit Sub
HasError:
   MsgBox Err.Description, vbCritical, psVBProjectName
   
End Sub

Private Sub cmbDrawShifrSearch_Click()
   'находим шифр чертежа в каталоге, и выделяем
   
   Dim strDrawShifr As String
   Dim objListItem As ListItem
   
   On Error GoTo HasError
   
   'если нет элементов в листвиевере
   If ListViewShifr.ListItems.count = 0 Then
       Exit Sub
   End If
   
   strDrawShifr = TextBoxDrawShifr
   If strDrawShifr = "" Then
'      'выделяем первый элемент листвевеа
'      If ListViewShifr.ListItems.Count <> 0 Then
'         Set objListItem = ListViewShifr.ListItems.Item(1)
'         ListViewShifr_ItemClick objListItem
'         Exit Sub
'      Else
'         Exit Sub
'      End If
      Exit Sub
   End If
   
   'получаем запись листвиевере по шифру чертежа
   Set objListItem = ListViewShifr.FindItem(strDrawShifr)
   If objListItem Is Nothing Then
      MsgBox "Нет такого шифра в каталоге!", vbExclamation, psVBProjectName
      Exit Sub
   End If
   
   objListItem.Selected = True
   
   'имитация клика, для обновления полей
   ListViewShifr_ItemClick objListItem

Exit Sub

HasError:
   Select Case Err.Number
      Case -2145386476 'Ключ не найден
         MsgBox "В каталоге нет такого шифра!?", vbExclamation, psVBProjectName
      Case 35601 'Ключ не найден
         MsgBox "В каталоге нет такого шифра!?", vbExclamation, psVBProjectName
      Case Else
         MsgBox Err.Description, vbCritical, psVBProjectName
   End Select
   
End Sub

Private Sub cmbSave_Click()
   'записи списка шифров в текстовый файл
   
   Dim objListItem As ListItem
   Dim strMacroFolder As String
   Dim strShifrTxtFullPath As String
   Dim strShifr As String
   Dim strAdress As String
   
   On Error GoTo HasError

   strMacroFolder = GetMacroFolder(psVBProjectName)
   strShifrTxtFullPath = strMacroFolder & "\Shifr.txt"
   
   If Dir(strShifrTxtFullPath) <> "" Then
      Kill strShifrTxtFullPath
   End If
   
   Open strShifrTxtFullPath For Output Access Write As #1
   
   For Each objListItem In ListViewShifr.ListItems
      'адрес проверяем, нет ли ентеров
      
      strShifr = objListItem.Text & ";" & objListItem.SubItems(1) & ";" & _
               objListItem.SubItems(2) & ";" & objListItem.SubItems(3) & ";" & _
               objListItem.SubItems(4) & ";" & objListItem.SubItems(5) & ";" & objListItem.SubItems(6) & ";" & _
               objListItem.SubItems(7) & ";" & objListItem.SubItems(8) & ";" & objListItem.SubItems(9)
      Print #1, strShifr
      
   Next
   
   Close #1
   
   cmbSave.Enabled = False

Exit Sub
HasError:
   MsgBox Err.Description, vbCritical, psVBProjectName
   
End Sub

Private Sub cmbSetShifrToDraw_Click()
   
   Dim objListItem As ListItem
   
'   strDaw = ThisDrawing.FullName
'   If strDaw = "" Then
'      strDaw = ThisDrawing.Name & " (не сохранен)"
'   End If
'   intOtvet = MsgBox(TextBoxShifr & " - установить текущему чертежу?" & vbCrLf & _
'                     strDaw, vbYesNo)
'   If intOtvet = 7 Then
'      Exit Sub
'   End If
   
   Set objListItem = ListViewShifr.SelectedItem
   
   If objListItem Is Nothing Then
      MsgBox "Не выбран шифр!", vbCritical, psVBProjectName
      Exit Sub
   End If
   
   'запись шифра в словарь
   If Functions.SetShifrToDict(objListItem.Text) = True Then
      MsgBox "Записано!", vbInformation, psVBProjectName
   Else
      MsgBox "Записать не удалось!", vbExclamation, psVBProjectName
   End If
   
End Sub

Private Sub cmbShifrAdd_Click()
   'добавлекние шифра
   
   Dim objListItem As ListItem
   
   'добавление нового шифра
   FormShifrRename.Caption = "Создание нового шифра"
   FormShifrRename.Show
   If FormShifrRename.ok = False Then
      'нажали отмену
      Exit Sub
   End If
   
   On Error GoTo HasError
   
'   'создаем новую запимь в листвиевере
'   Set objListItem = ListViewShifr.ListItems.Add(, , FormShifrRename.TextBoxShifr)
'   objListItem.SubItems(1) = FormShifrRename.TextBoxBS
'   objListItem.SubItems(2) = FormShifrRename.TextBoxPart
'   objListItem.SubItems(3) = FormShifrRename.ComboBoxSer
'   objListItem.SubItems(4) = FormShifrRename.TextBoxObjectName
'   objListItem.SubItems(5) = FormShifrRename.TextBoxAdress
'   objListItem.SubItems(6) = FormShifrRename.ComboBoxGIP
'   objListItem.SubItems(7) = FormShifrRename.ComboBoxClient
'   objListItem.SubItems(8) = FormShifrRename.ComboBoxFamNachOtd
'   objListItem.SubItems(9) = FormShifrRename.ComboBoxNachOtd
'   objListItem.SubItems(10) = FormShifrRename.ComboBoxGlSpec
   
   'добавляем запись в рекордсет
   objRecSet.AddNew
   objRecSet!Шифр = FormShifrRename.TextBoxShifr
   objRecSet!БС = FormShifrRename.TextBoxBS
   objRecSet!Часть = FormShifrRename.TextBoxPart
   objRecSet!Серия = FormShifrRename.ComboBoxSer
   objRecSet!Наимен_объекта = FormShifrRename.TextBoxObjectName
   objRecSet!Адрес = FormShifrRename.TextBoxAdress
   objRecSet!Заказчик = FormShifrRename.ComboBoxClient
   objRecSet!Должность1 = FormShifrRename.TextBoxPost1
   objRecSet!Фамилия1 = FormShifrRename.TextBoxFam1
   objRecSet!Должность2 = FormShifrRename.TextBoxPost2
   objRecSet!Фамилия2 = FormShifrRename.TextBoxFam2
   objRecSet!Должность3 = FormShifrRename.TextBoxPost3
   objRecSet!Фамилия3 = FormShifrRename.TextBoxFam3
   objRecSet!Должность4 = FormShifrRename.TextBoxPost4
   objRecSet!Фамилия4 = FormShifrRename.TextBoxFam4
   objRecSet!Стадия = FormShifrRename.TextBoxStage
   objRecSet.Update
   
   'обновление данных и листвиевера
   UserForm_Activate
   
   'найти и выделить добавленную строчку в таблице
   Set objListItem = ListViewShifr.FindItem(FormShifrRename.TextBoxShifr)
   If Not objListItem Is Nothing Then
      objListItem.Selected = True
      ListViewShifr_ItemClick objListItem
   End If
   
Exit Sub

HasError:
   Select Case Err.Number
      Case 94
         Resume Next
      Case -2147467259 'дублирование
         MsgBox "Такой шифр уже есть", vbCritical, psVBProjectName
      Case Else
         MsgBox Err.Description, vbCritical, psVBProjectName
   End Select
   
End Sub

Private Sub cmbShifrChange_Click()
   'редактирование шифра
   
   Dim objListItem As ListItem
   Dim strName As String
   Dim strSQL As String
   
   On Error GoTo HasError
   
   Set objListItem = ListViewShifr.SelectedItem
   If objListItem Is Nothing Then
      MsgBox "Нужно выбрать шифр в таблице!", vbInformation, psVBProjectName
      Exit Sub
   End If
   
   FormShifrRename.Show
   
   strName = FormShifrRename.TextBoxShifr
   If strName = "" Then Exit Sub
   If FormShifrRename.ok = False Then Exit Sub
      
   'находим запись в рекордсете и редактируем
   objRecSet.MoveFirst
   objRecSet.Find "Шифр = '" & objListItem & "'"
   If objRecSet.EOF Then
      MsgBox "Шифр не найден!", vbExclamation, psVBProjectName
      Exit Sub
   End If
   
'   objRecSet.Requery
   objRecSet!Шифр = FormShifrRename.TextBoxShifr
   objRecSet!БС = FormShifrRename.TextBoxBS
   objRecSet!Часть = FormShifrRename.TextBoxPart
   objRecSet!Серия = FormShifrRename.ComboBoxSer
   objRecSet!Наимен_объекта = FormShifrRename.TextBoxObjectName
   objRecSet!Адрес = FormShifrRename.TextBoxAdress
   objRecSet!Заказчик = FormShifrRename.ComboBoxClient
   objRecSet!Должность1 = FormShifrRename.TextBoxPost1
   objRecSet!Фамилия1 = FormShifrRename.TextBoxFam1
   objRecSet!Должность2 = FormShifrRename.TextBoxPost2
   objRecSet!Фамилия2 = FormShifrRename.TextBoxFam2
   objRecSet!Должность3 = FormShifrRename.TextBoxPost3
   objRecSet!Фамилия3 = FormShifrRename.TextBoxFam3
   objRecSet!Должность4 = FormShifrRename.TextBoxPost4
   objRecSet!Фамилия4 = FormShifrRename.TextBoxFam4
   objRecSet!Стадия = FormShifrRename.TextBoxStage
   objRecSet.Update
   
   'обновляем данные для шифа
   UserForm_Activate
   
   Set objListItem = ListViewShifr.FindItem(strName)
   ListViewShifr_ItemClick objListItem
   
Exit Sub

HasError:
   Select Case Err.Number
      Case 94
         Resume Next
      Case -2147467259 'нельзя удалить из базы, т.к. есть связанные данные
         MsgBox "Нельзя применить изменения, т.к. такой шифр уже есть!", vbExclamation, psVBProjectName
      Case Else
         MsgBox Err.Description, vbCritical, psVBProjectName
   End Select

End Sub

Private Sub cmbShifrDel_Click()
   'удаление выбранного шифра
   Dim objListItem As ListItem
   
   On Error GoTo HasError
   
   Set objListItem = ListViewShifr.SelectedItem
   
   If objListItem Is Nothing Then
      MsgBox "Не выбран шифр в списке!", vbInformation, psVBProjectName
      Exit Sub
   End If
   
   'подтверждение удаления шифра из базы
   If MsgBox("Удалить шифр - " & objListItem & " из каталога?", vbQuestion + vbYesNo, psVBProjectName) = vbNo Then Exit Sub
   
   'удаляем из рекордсета
   objRecSet.MoveFirst
   objRecSet.Find "Шифр = '" & objListItem.Text & "'"
   If objRecSet.EOF Then
      'не найден шифр в базе
      Exit Sub
   End If
   objRecSet.Delete
   objRecSet.Update
   
   'удаление выделенного шифра из листвиевера
   ListViewShifr.ListItems.Remove objListItem.index
   
   ListViewShifr.ListItems.Item(1).Selected = True
   
Exit Sub
HasError:
   MsgBox Err.Description, vbCritical, psVBProjectName
   
End Sub


Private Sub ListViewShifr_ColumnClick(ByVal columnHeader As MSComctlLib.columnHeader)
   'сортируем по выбранной колонке
   Dim keyBefore As Integer
   keyBefore = ListViewShifr.SortKey
   Select Case columnHeader.Text
      Case "Шифр"
         ListViewShifr.SortKey = 0
      Case "(бс)"
         ListViewShifr.SortKey = 1
      Case "Часть"
         ListViewShifr.SortKey = 2
      Case "Серия"
         ListViewShifr.SortKey = 3
      Case "Объект"
         ListViewShifr.SortKey = 4
      Case "Адрес"
         ListViewShifr.SortKey = 5
      Case "Заказчик"
         ListViewShifr.SortKey = 6
      Case "Должность1"
         ListViewShifr.SortKey = 7
      Case "Фамилия1"
         ListViewShifr.SortKey = 8
      Case "Должность2"
         ListViewShifr.SortKey = 9
      Case "Фамилия2"
         ListViewShifr.SortKey = 10
      Case "Должность3"
         ListViewShifr.SortKey = 11
      Case "Фамилия3"
         ListViewShifr.SortKey = 12
      Case "Должность4"
         ListViewShifr.SortKey = 13
      Case "Фамилия4"
         ListViewShifr.SortKey = 14
      Case "Стадия"
         ListViewShifr.SortKey = 15
      Case "Дата создания"
         ListViewShifr.SortKey = 16
   End Select
   If keyBefore = ListViewShifr.SortKey Then
      'меняем порядок сортировки
      If ListViewShifr.SortOrder = lvwAscending Then
         ListViewShifr.SortOrder = lvwDescending
      Else
         ListViewShifr.SortOrder = lvwAscending
      End If
   End If
End Sub

Private Sub ListViewShifr_ItemClick(ByVal Item As MSComctlLib.ListItem)
   'заполняем поля данныз выбранного шифра
      
   On Error GoTo HasError
      
   If Item.SubItems(1) = "" Then
      CheckBoxOsnKomplect.Visible = False
   Else
      CheckBoxOsnKomplect.Visible = True
      CheckBoxOsnKomplect.Value = False
   End If
   
   TextBoxShifr = Item.Text & "-" & Item.SubItems(2)
   TextBoxClient = Item.SubItems(6)
   TextBoxAdress = Item.SubItems(5)
   TextBoxObjectName = Item.SubItems(4)
   TextBoxPost1 = Item.SubItems(7)
   TextBoxFam1 = Item.SubItems(8)
   TextBoxPost2 = Item.SubItems(9)
   TextBoxFam2 = Item.SubItems(10)
   TextBoxPost3 = Item.SubItems(11)
   TextBoxFam3 = Item.SubItems(12)
   TextBoxPost4 = Item.SubItems(13)
   TextBoxFam4 = Item.SubItems(14)
   TextBoxStage = Item.SubItems(15)

Exit Sub
HasError:
   If Err.Number = 94 Then
      Resume Next
   End If
   MsgBox Err.Description
End Sub

Private Sub cmbExit_Click()
   
   'подтверждение выхода
   
'   Dim intOtvet As Integer
'   Dim strKompName As String
'
'   'проверяем статус редактирования базы
'   If bolBaseWriteRead = True Then
'      If bolIzm = True Then
'         If MsgBox("Cохранить изменения?", vbYesNo) = vbYes Then
'            cmbSave_Click
'            hide
'         Else
'            hide
'         End If
'      End If
'      'удаляем файл статуса редактирования базы шифров
'      ShifrEditDel
'   End If
   
   If objConect.State = adStateOpen Then objConect.Close
   
   Hide
   
End Sub

Private Sub UserForm_KeyDown(ByVal KeyCode As MSForms.ReturnInteger, ByVal Shift As Integer)

End Sub

Private Sub UserForm_QueryClose(Cancel As Integer, CloseMode As Integer)
   
   cmbExit_Click
   
End Sub

Private Sub ShifrEditDel()
   'удаляем файл редактирования базы шифров
      
   Dim strShifrEditTxt As String
   
   On Error GoTo HasError
   
   'файл статуса редактрирования базы шифра
   strShifrEditTxt = Functions.GetMacroFolder(psVBProjectName) & "\Shifr_Edit.txt"
   
   'удаляем его
   Kill strShifrEditTxt
   
Exit Sub
HasError:
   MsgBox Err.Description, vbCritical, psVBProjectName
   
End Sub

Attribute VB_Name = "FormShifrRename"
Attribute VB_Base = "0{02D84813-5370-4F29-AA2F-93DCFFECA63F}{04722747-0037-4369-A1B7-000D1CBBA414}"
Attribute VB_GlobalNameSpace = False
Attribute VB_Creatable = False
Attribute VB_PredeclaredId = True
Attribute VB_Exposed = False
Attribute VB_TemplateDerived = False
Attribute VB_Customizable = False
Option Explicit

Public ok As Boolean

Private Sub cmbCancel_Click()
   TextBoxShifr = ""
   ok = False
   Hide
End Sub

Private Sub cmbDelClient_Click()
   'удаление заказчика из комбобокса и базы
   
   Dim index As Integer
   Dim strSQL As String
   Dim objRec As New ADODB.Recordset
   Dim strName As String
   
   On Error GoTo HasError
   
   index = ComboBoxClient.ListIndex
   If index = -1 Then
      MsgBox "Не выбран заказчик", vbCritical, psVBProjectName
      Exit Sub
   End If
   
   'предупреждение
   If MsgBox("Удалить заказчика?", vbQuestion + vbYesNo, psVBProjectName) = vbNo Then Exit Sub
'   If MsgBox("Будут удалены все шифры этой серии! Продолжить?", vbQuestion + vbYesNo) = vbNo Then Exit Sub
   
   'запрос серий из таблицы Серии
   strSQL = "SELECT Название FROM Заказчики WHERE Название = '" & ComboBoxClient & "'"
   objRec.Open Source:=strSQL, ActiveConnection:=objConect, _
                  CursorType:=adOpenKeyset, LockType:=adLockOptimistic, Options:=adCmdText
   If objRec.EOF And objRec.BOF Then
      MsgBox "Такого заказчика нет!", vbInformation, psVBProjectName
      Exit Sub
   End If
   
   objRec.Delete
   objRec.Update
   
   ComboBoxClient.RemoveItem index
   ComboBoxClient.ListIndex = 0

Exit Sub
   
HasError:
   Select Case Err.Number
      Case -2147467259 'нельзя удалить из базы, т.к. есть связанные данные
         MsgBox "Нельзя удалить, т.к. есть шифры ссылающиеся на этого заказчика!", vbCritical, psVBProjectName
      Case Else
         MsgBox Err.Description, vbCritical, psVBProjectName
   End Select
End Sub

'Private Sub cmbDelGIP_Click()
'   'удаление заказчика из комбобокса и базы
'
'   Dim index As Integer
'   Dim strSQL As String
'   Dim objRec As New ADODB.Recordset
'   Dim strName As String
'
'   On Error GoTo HasError
'
'   index = ComboBoxGIP.ListIndex
'   If index = -1 Then
'      MsgBox "Не выбран ГИП", vbCritical, psVBProjectName
'      Exit Sub
'   End If
'
'   'предупреждение
'   If MsgBox("Удалить ГИПа?", vbQuestion + vbYesNo, psVBProjectName) = vbNo Then Exit Sub
''   If MsgBox("Будут удалены все шифры этой серии! Продолжить?", vbQuestion + vbYesNo) = vbNo Then Exit Sub
'
'   'запрос серий из таблицы ГИПов
'   strSQL = "SELECT Фамилия FROM ГИПЫ WHERE Фамилия = '" & ComboBoxGIP & "'"
'   objRec.Open Source:=strSQL, ActiveConnection:=objConect, _
'                  CursorType:=adOpenKeyset, LockType:=adLockOptimistic, Options:=adCmdText
'   If objRec.EOF And objRec.BOF Then
'      MsgBox "Такого ГИПа нет!", vbInformation, psVBProjectName
'      Exit Sub
'   End If
'   objRec.Delete
'   objRec.Update
'
'   ComboBoxGIP.RemoveItem index
'   ComboBoxGIP.ListIndex = 0
'
'Exit Sub
'
'HasError:
'   Select Case Err.Number
'      Case -2147467259 'нельзя удалить из базы, т.к. есть связанные данные
'         MsgBox "Нельзя удалить, т.к. есть шифры ссылающиеся на этого ГИПа!", vbCritical, psVBProjectName
'      Case Else
'         MsgBox Err.Description, vbCritical, psVBProjectName
'   End Select
'End Sub

'Private Sub cmbDelGlSpec_Click()
'   'удаление гл.спеца из комбобокса и базы
'
'   Dim index As Integer
'   Dim strSQL As String
'   Dim objRec As New ADODB.Recordset
'   Dim strName As String
'
'   On Error GoTo HasError
'
'   index = ComboBoxGlSpec.ListIndex
'   If index = -1 Then
'      MsgBox "Не выбран гл.спец.", vbCritical, psVBProjectName
'      Exit Sub
'   End If
'
'   'предупреждение
'   If MsgBox("Удалить гл.спец.?", vbQuestion + vbYesNo, psVBProjectName) = vbNo Then Exit Sub
''   If MsgBox("Будут удалены все шифры этой серии! Продолжить?", vbQuestion + vbYesNo) = vbNo Then Exit Sub
'
'   'запрос серий из таблицы Нач_отд
'   strSQL = "SELECT Фамилия FROM Гл_спецы WHERE Фамилия = '" & ComboBoxGlSpec & "'"
'   objRec.Open Source:=strSQL, ActiveConnection:=objConect, _
'                  CursorType:=adOpenKeyset, LockType:=adLockOptimistic, Options:=adCmdText
'   If objRec.EOF And objRec.BOF Then
'      MsgBox "Такого гл.спец. нет!", vbCritical, psVBProjectName
'      Exit Sub
'   End If
'
'   objRec.Delete
'   objRec.Update
'
'   ComboBoxGlSpec.RemoveItem index
'   ComboBoxGlSpec.ListIndex = 0
'
'Exit Sub
'
'HasError:
'   Select Case Err.Number
'      Case -2147467259 'нельзя удалить из базы, т.к. есть связанные данные
'         MsgBox "Нельзя удалить, т.к. есть шифры ссылающиеся на этого гл.спец.!", vbCritical, psVBProjectName
'      Case Else
'         MsgBox Err.Description, vbCritical, psVBProjectName
'   End Select
'End Sub

'Private Sub cmbDelAKM_Click()
'   'удаление Нач.АКМ из комбобокса и базы
'
'   Dim index As Integer
'   Dim strSQL As String
'   Dim objRec As New ADODB.Recordset
'   Dim strName As String
'
'   On Error GoTo HasError
'
'   index = ComboBoxAKM.ListIndex
'   If index = -1 Then
'      MsgBox "Не выбран нач.АКМ.", vbCritical, psVBProjectName
'      Exit Sub
'   End If
'
'   'предупреждение
'   If MsgBox("Удалить нач.AKM?", vbQuestion + vbYesNo, psVBProjectName) = vbNo Then Exit Sub
'
'   'запрос серий из таблицы Нач_акм
'   strSQL = "SELECT Фамилия FROM Нач_акм WHERE Фамилия = '" & ComboBoxAKM & "'"
'   objRec.Open Source:=strSQL, ActiveConnection:=objConect, _
'                  CursorType:=adOpenKeyset, LockType:=adLockOptimistic, Options:=adCmdText
'   If objRec.EOF And objRec.BOF Then
'      MsgBox "Такого начальника АКМ нет!", vbCritical, psVBProjectName
'      Exit Sub
'   End If
'
'   objRec.Delete
'   objRec.Update
'
'   ComboBoxAKM.RemoveItem index
'   ComboBoxAKM.ListIndex = 0
'
'Exit Sub
'
'HasError:
'   Select Case Err.Number
'      Case -2147467259 'нельзя удалить из базы, т.к. есть связанные данные
'         MsgBox "Нельзя удалить, т.к. есть шифры ссылающиеся на этого нач.АКМ!", vbCritical, psVBProjectName
'      Case Else
'         MsgBox Err.Description, vbCritical, psVBProjectName
'   End Select
'End Sub
'
'Private Sub cmbDelSPD_Click()
'   'удаление Нач.СПД из комбобокса и базы
'
'   Dim index As Integer
'   Dim strSQL As String
'   Dim objRec As New ADODB.Recordset
'   Dim strName As String
'
'   On Error GoTo HasError
'
'   index = ComboBoxSPD.ListIndex
'   If index = -1 Then
'      MsgBox "Не выбран нач.СПД.", vbCritical, psVBProjectName
'      Exit Sub
'   End If
'
'   'предупреждение
'   If MsgBox("Удалить нач.СПД?", vbQuestion + vbYesNo, psVBProjectName) = vbNo Then Exit Sub
'
'   'запрос серий из таблицы Нач_спд
'   strSQL = "SELECT Фамилия FROM Нач_спд WHERE Фамилия = '" & ComboBoxSPD & "'"
'   objRec.Open Source:=strSQL, ActiveConnection:=objConect, _
'                  CursorType:=adOpenKeyset, LockType:=adLockOptimistic, Options:=adCmdText
'   If objRec.EOF And objRec.BOF Then
'      MsgBox "Такого начальника СПД нет!", vbCritical, psVBProjectName
'      Exit Sub
'   End If
'
'   objRec.Delete
'   objRec.Update
'
'   ComboBoxSPD.RemoveItem index
'   ComboBoxSPD.ListIndex = 0
'
'Exit Sub
'
'HasError:
'   Select Case Err.Number
'      Case -2147467259 'нельзя удалить из базы, т.к. есть связанные данные
'         MsgBox "Нельзя удалить, т.к. есть шифры ссылающиеся на этого нач.СПД!", vbCritical, psVBProjectName
'      Case Else
'         MsgBox Err.Description, vbCritical, psVBProjectName
'   End Select
'End Sub

Private Sub cmbDelSer_Click()
   'удаление серии из комбобокса и базы
   
   Dim index As Integer
   Dim strSQL As String
   Dim objRec As New ADODB.Recordset
   Dim strName As String
   
   On Error GoTo HasError
   
   index = ComboBoxSer.ListIndex
   If index = -1 Then
      MsgBox "Не выбрана серия", vbCritical, psVBProjectName
      Exit Sub
   End If
   
   'предупреждение
   If MsgBox("Удалить серию?", vbQuestion + vbYesNo, psVBProjectName) = vbNo Then Exit Sub
   
   'запрос серий из таблицы Серии
   strSQL = "SELECT Имя FROM Серии WHERE Имя = '" & ComboBoxSer & "'"
   objRec.Open Source:=strSQL, ActiveConnection:=objConect, _
                  CursorType:=adOpenKeyset, LockType:=adLockOptimistic, Options:=adCmdText
   If objRec.EOF And objRec.BOF Then
      MsgBox "Такой серии нет!", vbCritical, psVBProjectName
      Exit Sub
   End If
   
   objRec.Delete
   objRec.Update
   
   ComboBoxSer.RemoveItem index
   ComboBoxSer.ListIndex = 0

Exit Sub
   
HasError:
   Select Case Err.Number
      Case -2147467259 'нельзя удалить из базы, т.к. есть связанные данные
         MsgBox "Нельзя удалить, т.к. есть шифры ссылающиеся на эту серию!", vbCritical, psVBProjectName
      Case Else
         MsgBox Err.Description, vbCritical, psVBProjectName
   End Select
   
End Sub

Private Sub cmbEditClient_Click()
   'редактирование заказчика в комбобокса и базы
   
   Dim index As Integer
   Dim strSQL As String
   Dim objRec As New ADODB.Recordset
   Dim strName As String
   
   On Error GoTo HasError
   
   index = ComboBoxClient.ListIndex
   If index = -1 Then
      MsgBox "Не выбран заказчик", vbCritical, psVBProjectName
      Exit Sub
   End If
   
'   'предупреждение
'   If MsgBox("Изменения будут внесены во все шифры по этой серии! Продолжить?", vbQuestion + vbYesNo) = vbNo Then Exit Sub
   
   strName = ComboBoxClient
   'запрос нового имени
   FormInput.Caption = "Изменение заказчика"
   FormInput.TextBoxName = strName
   FormInput.Show
   If FormInput.TextBoxName = "" Then Exit Sub
   If FormInput.TextBoxName = strName Then
      'не изменилось имя
      Exit Sub
   End If
   
   'запрос заказчиков
   strSQL = "SELECT Название FROM Заказчики WHERE Название = '" & ComboBoxClient & "'"
   objRec.Open Source:=strSQL, ActiveConnection:=objConect, _
                  CursorType:=adOpenKeyset, LockType:=adLockOptimistic, Options:=adCmdText
   If objRec.EOF And objRec.BOF Then
      MsgBox "Такого заказчика нет!", vbCritical, psVBProjectName
      Exit Sub
   End If
   objRec!Название = FormInput.TextBoxName
   
   objRec.Update
   
   'редактируем имя в комбобоксе
   ComboBoxClient.List(index, 0) = FormInput.TextBoxName

Exit Sub

HasError:
   Select Case Err.Number
      Case -2147467259 'нельзя удалить из базы, т.к. есть связанные данные
         MsgBox "Нельзя изменить, т.к. токой заказчик уже есть!", vbCritical, psVBProjectName
      Case Else
         MsgBox Err.Description, vbCritical, psVBProjectName
   End Select

End Sub

'Private Sub cmbEditGIP_Click()
'   'редактирование ГИПа в комбобокса и базы
'
'   Dim index As Integer
'   Dim strSQL As String
'   Dim objRec As New ADODB.Recordset
'   Dim strName As String
'
'   On Error GoTo HasError
'
'   index = ComboBoxGIP.ListIndex
'   If index = -1 Then
'      MsgBox "Не выбран ГИП", vbCritical, psVBProjectName
'      Exit Sub
'   End If
'
''   'предупреждение
''   If MsgBox("Изменения будут внесены во все шифры по этой серии! Продолжить?", vbQuestion + vbYesNo) = vbNo Then Exit Sub
'
'   strName = ComboBoxGIP
'   'запрос нового имени
'   FormInput.Caption = "Изменение ГИПа"
'   FormInput.TextBoxName = strName
'   FormInput.Show
'   If FormInput.TextBoxName = "" Then Exit Sub
'   If FormInput.TextBoxName = strName Then
'      'не изменилось имя
'      Exit Sub
'   End If
'
'   'запрос заказчиков
'   strSQL = "SELECT Фамилия FROM ГИПЫ WHERE Фамилия = '" & ComboBoxGIP & "'"
'   objRec.Open Source:=strSQL, ActiveConnection:=objConect, _
'                  CursorType:=adOpenKeyset, LockType:=adLockOptimistic, Options:=adCmdText
'   If objRec.EOF And objRec.BOF Then
'      MsgBox "Такого ГИПа нет!", vbCritical, psVBProjectName
'      Exit Sub
'   End If
'   objRec!Фамилия = FormInput.TextBoxName
'
'   objRec.Update
'
'   'редактируем имя в комбобоксе
'   ComboBoxGIP.List(index, 0) = FormInput.TextBoxName
'
'Exit Sub
'
'HasError:
'   Select Case Err.Number
'      Case -2147467259 'нельзя удалить из базы, т.к. есть связанные данные
'         MsgBox "Нельзя изменить, т.к. токой ГИП уже есть!", vbCritical, psVBProjectName
'      Case Else
'         MsgBox Err.Description, vbCritical, psVBProjectName
'   End Select
'
'End Sub
'
'Private Sub cmbEditGlSpec_Click()
'   'редактирование гл.спец. в комбобокса и базы
'
'   Dim index As Integer
'   Dim strSQL As String
'   Dim objRec As New ADODB.Recordset
'   Dim strName As String
'
'   On Error GoTo HasError
'
'   index = ComboBoxGlSpec.ListIndex
'   If index = -1 Then
'      MsgBox "Не выбран гл.спец.", vbCritical, psVBProjectName
'      Exit Sub
'   End If
'
''   'предупреждение
''   If MsgBox("Изменения будут внесены во все шифры по этой серии! Продолжить?", vbQuestion + vbYesNo) = vbNo Then Exit Sub
'
'   strName = ComboBoxGlSpec
'   'запрос нового имени
'   FormInput.Caption = "Изменение гл.спец."
'   FormInput.TextBoxName = strName
'   FormInput.Show
'   If FormInput.TextBoxName = "" Then Exit Sub
'   If FormInput.TextBoxName = strName Then
'      'не изменилось имя
'      Exit Sub
'   End If
'
'   'запрос заказчиков
'   strSQL = "SELECT Фамилия FROM Гл_спецы WHERE Фамилия = '" & ComboBoxGlSpec & "'"
'   objRec.Open Source:=strSQL, ActiveConnection:=objConect, _
'                  CursorType:=adOpenKeyset, LockType:=adLockOptimistic, Options:=adCmdText
'   If objRec.EOF And objRec.BOF Then
'      MsgBox "Такого заказчика нет!", vbCritical, psVBProjectName
'      Exit Sub
'   End If
'   objRec!Фамилия = FormInput.TextBoxName
'
'   objRec.Update
'
'   'редактируем имя в комбобоксе
'   ComboBoxGlSpec.List(index, 0) = FormInput.TextBoxName
'
'Exit Sub
'
'HasError:
'   Select Case Err.Number
'      Case -2147467259 'нельзя удалить из базы, т.к. есть связанные данные
'         MsgBox "Нельзя изменить, т.к. токой гл.спец. уже есть!", vbCritical, psVBProjectName
'      Case Else
'         MsgBox Err.Description, vbCritical, psVBProjectName
'   End Select
'End Sub
'
'Private Sub cmbEditAKM_Click()
'   'редактирование Нач.акм в комбобокса и базы
'
'   Dim index As Integer
'   Dim strSQL As String
'   Dim objRec As New ADODB.Recordset
'   Dim strName As String
'
'   On Error GoTo HasError
'
'   index = ComboBoxAKM.ListIndex
'   If index = -1 Then
'      MsgBox "Не выбран нач.акм", vbCritical, psVBProjectName
'      Exit Sub
'   End If
'
'   strName = ComboBoxAKM
'   'запрос нового имени
'   FormInput.Caption = "Изменение нач.АКМ"
'   FormInput.TextBoxName = strName
'   FormInput.Show
'   If FormInput.TextBoxName = "" Then Exit Sub
'   If FormInput.TextBoxName = strName Then
'      'не изменилось имя
'      Exit Sub
'   End If
'
'   'запрос фамилии
'   strSQL = "SELECT Фамилия FROM Нач_акм WHERE Фамилия = '" & ComboBoxAKM & "'"
'   objRec.Open Source:=strSQL, ActiveConnection:=objConect, _
'                  CursorType:=adOpenKeyset, LockType:=adLockOptimistic, Options:=adCmdText
'   If objRec.EOF And objRec.BOF Then
'      MsgBox "Такой фамилии нет!", vbCritical, psVBProjectName
'      Exit Sub
'   End If
'   objRec!Фамилия = FormInput.TextBoxName
'
'   objRec.Update
'
'   'редактируем имя в комбобоксе
'   ComboBoxAKM.List(index, 0) = FormInput.TextBoxName
'
'Exit Sub
'
'HasError:
'   Select Case Err.Number
'      Case -2147467259 'нельзя удалить из базы, т.к. есть связанные данные
'         MsgBox "Нельзя изменить, т.к. токой нач.АКМ уже есть!", vbCritical, psVBProjectName
'      Case Else
'         MsgBox Err.Description, vbCritical, psVBProjectName
'   End Select
'
'End Sub
'
'Private Sub cmbEditSPD_Click()
'   'редактирование Нач.спд в комбобокса и базы
'
'   Dim index As Integer
'   Dim strSQL As String
'   Dim objRec As New ADODB.Recordset
'   Dim strName As String
'
'   On Error GoTo HasError
'
'   index = ComboBoxSPD.ListIndex
'   If index = -1 Then
'      MsgBox "Не выбран нач.спд", vbCritical, psVBProjectName
'      Exit Sub
'   End If
'
'   strName = ComboBoxSPD
'   'запрос нового имени
'   FormInput.Caption = "Изменение фамилии нач.СПД"
'   FormInput.TextBoxName = strName
'   FormInput.Show
'   If FormInput.TextBoxName = "" Then Exit Sub
'   If FormInput.TextBoxName = strName Then
'      'не изменилось имя
'      Exit Sub
'   End If
'
'   'запрос фамилии
'   strSQL = "SELECT Фамилия FROM Нач_спд WHERE Фамилия = '" & ComboBoxSPD & "'"
'   objRec.Open Source:=strSQL, ActiveConnection:=objConect, _
'                  CursorType:=adOpenKeyset, LockType:=adLockOptimistic, Options:=adCmdText
'   If objRec.EOF And objRec.BOF Then
'      MsgBox "Такой фамилии нет!", vbCritical, psVBProjectName
'      Exit Sub
'   End If
'   objRec!Фамилия = FormInput.TextBoxName
'
'   objRec.Update
'
'   'редактируем имя в комбобоксе
'   ComboBoxSPD.List(index, 0) = FormInput.TextBoxName
'
'Exit Sub
'
'HasError:
'   Select Case Err.Number
'      Case -2147467259 'нельзя удалить из базы, т.к. есть связанные данные
'         MsgBox "Нельзя изменить, т.к. токой нач.СПД уже есть!", vbCritical, psVBProjectName
'      Case Else
'         MsgBox Err.Description, vbCritical, psVBProjectName
'   End Select
'
'End Sub

Private Sub cmbEditSer_Click()
   'редактирование серии в комбобокса и базы
   
   Dim index As Integer
   Dim strSQL As String
   Dim objRec As New ADODB.Recordset
   Dim strName As String
   
   On Error GoTo HasError
   
   index = ComboBoxSer.ListIndex
   If index = -1 Then
      MsgBox "Не выбрана серия", vbCritical, psVBProjectName
      Exit Sub
   End If
   
'   'предупреждение
'   If MsgBox("Изменения будут внесены во все шифры по этой серии! Продолжить?", vbQuestion + vbYesNo) = vbNo Then Exit Sub
   
   strName = ComboBoxSer
   'запрос нового имени
   FormInput.Caption = "Переименование серии"
   FormInput.TextBoxName = strName
   FormInput.Show
   If FormInput.TextBoxName = "" Then Exit Sub
   If FormInput.TextBoxName = strName Then
      'не изменилось имя
      Exit Sub
   End If
   
   'запрос серий из таблицы Серии
   strSQL = "SELECT Имя FROM Серии WHERE Имя = '" & ComboBoxSer & "'"
   objRec.Open Source:=strSQL, ActiveConnection:=objConect, _
                  CursorType:=adOpenKeyset, LockType:=adLockOptimistic, Options:=adCmdText
   If objRec.EOF And objRec.BOF Then
      MsgBox "Такой серии нет!", vbCritical, psVBProjectName
      Exit Sub
   End If
   objRec!Имя = FormInput.TextBoxName
   
   objRec.Update
   
   'редактируем имя в комбобоксе
   ComboBoxSer.List(index, 0) = FormInput.TextBoxName

Exit Sub

HasError:
   Select Case Err.Number
      Case -2147467259 'нельзя удалить из базы, т.к. есть связанные данные
         MsgBox "Нельзя изменить, т.к. такая серия уже есть!", vbCritical, psVBProjectName
      Case Else
         MsgBox Err.Description, vbCritical, psVBProjectName
   End Select

End Sub

Private Sub cmbNewClient_Click()
   'создание нового заказчика
   
   Dim objListItem As ListItem
   Dim strSQL As String
   Dim objRec As New ADODB.Recordset
   Dim strName As String
   
   On Error GoTo HasError
   
   'запрос имени заказчика
   FormInput.Caption = "Новый заказчик"
   FormInput.Show
   strName = FormInput.TextBoxName
   If strName = "" Then
      'нажали отмену
      Exit Sub
   End If
      
   'запрос таблицы заказчиков
   strSQL = "SELECT Название FROM Заказчики ORDER BY Название"
   objRec.Open Source:=strSQL, ActiveConnection:=objConect, _
                  CursorType:=adOpenKeyset, LockType:=adLockOptimistic, Options:=adCmdText
   
   'нужно добавить обработчик ошибки дублирующегося имени
   objRec.AddNew
   objRec!Название = strName
   objRec.Update
   
   'добавление записи в комбобокс
   ComboBoxClient.AddItem strName
   ComboBoxClient = strName
      
Exit Sub

HasError:
   Select Case Err.Number
      Case -2147467259 'дублирование
         MsgBox "Такой заказчик уже есть", vbCritical, psVBProjectName
      Case Else
         MsgBox Err.Description, vbCritical, psVBProjectName
   End Select
   
End Sub

'Private Sub cmbNewGIP_Click()
'   'создание нового ГИПа
'
'   Dim objListItem As ListItem
'   Dim strSQL As String
'   Dim objRec As New ADODB.Recordset
'   Dim strName As String
'
'   On Error GoTo HasError
'
'   'запрос имени ГИПа
'   FormInput.Caption = "Новый ГИП"
'   FormInput.Show
'   strName = FormInput.TextBoxName
'   If strName = "" Then
'      'нажали отмену
'      Exit Sub
'   End If
'
'   'запрос таблицы ГИПов
'   strSQL = "SELECT Фамилия FROM ГИПЫ ORDER BY Фамилия"
'   objRec.Open Source:=strSQL, ActiveConnection:=objConect, _
'                  CursorType:=adOpenKeyset, LockType:=adLockOptimistic, Options:=adCmdText
'
'   'нужно добавить обработчик ошибки дублирующегося имени
'   objRec.AddNew
'   objRec!Фамилия = strName
'   objRec.Update
'
'   'добавление записи в комбобокс
'   ComboBoxGIP.AddItem strName
'   ComboBoxGIP = strName
'
'Exit Sub
'
'HasError:
'   Select Case Err.Number
'      Case -2147467259 'дублирование
'         MsgBox "Такой ГИП уже есть", vbCritical, psVBProjectName
'      Case Else
'         MsgBox Err.Description, vbCritical, psVBProjectName
'   End Select
'
'End Sub
'
'Private Sub cmbNewGlSpec_Click()
'   'создание нового Нач.отдела
'
'   Dim objListItem As ListItem
'   Dim strSQL As String
'   Dim objRec As New ADODB.Recordset
'   Dim strName As String
'
'   On Error GoTo HasError
'
'   'запрос имени Гл.спец
'   FormInput.Caption = "Новый Гл.специалист"
'   FormInput.Show
'   strName = FormInput.TextBoxName
'   If strName = "" Then
'      'нажали отмену
'      Exit Sub
'   End If
'
'   'запрос таблицы заказчиков
'   strSQL = "SELECT Фамилия FROM Гл_спецы ORDER BY Фамилия"
'   objRec.Open Source:=strSQL, ActiveConnection:=objConect, _
'               CursorType:=adOpenKeyset, LockType:=adLockOptimistic, Options:=adCmdText
'
'   'нужно добавить обработчик ошибки дублирующегося имени
'   objRec.AddNew
'   objRec!Фамилия = strName
'   objRec.Update
'
'   'добавление записи в комбобокс
'   ComboBoxGlSpec.AddItem strName
'   ComboBoxGlSpec = strName
'
'Exit Sub
'
'HasError:
'   Select Case Err.Number
'      Case -2147467259 'дублирование
'         MsgBox "Такой гл.специалист уже есть", vbCritical, psVBProjectName
'      Case Else
'         MsgBox Err.Description, vbCritical, psVBProjectName
'   End Select
'End Sub
'
'Private Sub cmbNewAKM_Click()
'   'создание нового Нач.АКМ
'
'   Dim objListItem As ListItem
'   Dim strSQL As String
'   Dim objRec As New ADODB.Recordset
'   Dim strName As String
'
'   On Error GoTo HasError
'
'   'запрос имени Нач.АКМ
'   FormInput.Caption = "Новый нач.АКМ"
'   FormInput.Show
'   strName = FormInput.TextBoxName
'   If strName = "" Then
'      'нажали отмену
'      Exit Sub
'   End If
'
'   'запрос таблицы фамилий
'   strSQL = "SELECT Фамилия FROM Нач_акм ORDER BY Фамилия"
'   objRec.Open Source:=strSQL, ActiveConnection:=objConect, _
'               CursorType:=adOpenKeyset, LockType:=adLockOptimistic, Options:=adCmdText
'
'   'нужно добавить обработчик ошибки дублирующегося имени
'   objRec.AddNew
'   objRec!Фамилия = strName
'   objRec.Update
'
'   'добавление записи в комбобокс
'   ComboBoxAKM.AddItem strName
'   ComboBoxAKM = strName
'
'Exit Sub
'
'HasError:
'   Select Case Err.Number
'      Case -2147467259 'дублирование
'         MsgBox "Такой нач.АКМ уже есть", vbCritical, psVBProjectName
'      Case Else
'         MsgBox Err.Description, vbCritical, psVBProjectName
'   End Select
'End Sub
'
'Private Sub cmbNewSPD_Click()
'   'создание нового Нач.СПД
'
'   Dim objListItem As ListItem
'   Dim strSQL As String
'   Dim objRec As New ADODB.Recordset
'   Dim strName As String
'
'   On Error GoTo HasError
'
'   'запрос имени Нач.СПД
'   FormInput.Caption = "Новый нач.СПД"
'   FormInput.Show
'   strName = FormInput.TextBoxName
'   If strName = "" Then
'      'нажали отмену
'      Exit Sub
'   End If
'
'   'запрос таблицы фамилий
'   strSQL = "SELECT Фамилия FROM Нач_спд ORDER BY Фамилия"
'   objRec.Open Source:=strSQL, ActiveConnection:=objConect, _
'               CursorType:=adOpenKeyset, LockType:=adLockOptimistic, Options:=adCmdText
'
'   'нужно добавить обработчик ошибки дублирующегося имени
'   objRec.AddNew
'   objRec!Фамилия = strName
'   objRec.Update
'
'   'добавление записи в комбобокс
'   ComboBoxSPD.AddItem strName
'   ComboBoxSPD = strName
'
'Exit Sub
'
'HasError:
'   Select Case Err.Number
'      Case -2147467259 'дублирование
'         MsgBox "Такой нач.СПД уже есть", vbCritical, psVBProjectName
'      Case Else
'         MsgBox Err.Description, vbCritical, psVBProjectName
'   End Select
'End Sub


Private Sub cmbNewSer_Click()
   'создание новой серии
   
   Dim objListItem As ListItem
   Dim strSQL As String
   Dim objRec As New ADODB.Recordset
   Dim strName As String
   
   On Error GoTo HasError
   
   'запрос имени серии
   FormInput.Caption = "Новая серия"
   FormInput.Show
   strName = FormInput.TextBoxName
   If strName = "" Then
      'нажали отмену
      Exit Sub
   End If
      
   'запрос таблицы серий
   strSQL = "SELECT Имя FROM Серии ORDER BY Имя;"
   objRec.Open Source:=strSQL, ActiveConnection:=objConect, _
                  CursorType:=adOpenKeyset, LockType:=adLockOptimistic, Options:=adCmdText
   'нужно добавить обработчик ошибки дублирующегося имени
   
   objRec.AddNew
   objRec!Имя = strName
   objRec.Update
   
   'добавление записи в комбобокс
   ComboBoxSer.AddItem strName
   ComboBoxSer = strName
   
Exit Sub

HasError:
   Select Case Err.Number
      Case -2147467259 'дублирование
         MsgBox "Такая серия уже есть", vbCritical, psVBProjectName
      Case Else
         MsgBox Err.Description, vbCritical, psVBProjectName
   End Select
   
End Sub

Private Sub cmbOK_Click()
   'вносим изменение в текущую запись листвиевера
   
   'тут нужны проверки введенных данных
   If TextBoxShifr = "" Then
      MsgBox "Поле шифра не заполнено!", vbCritical, psVBProjectName
      Exit Sub
   End If
   
   ok = True
   
   Hide
   
End Sub

Private Sub ComboBoxClient_Change()
   ComboBoxClient.ControlTipText = ComboBoxClient.Text
End Sub

Private Sub UserForm_Activate()

   Dim objListItem As ListItem
   Dim strSQL As String
   Dim objRec As New ADODB.Recordset
   
   On Error GoTo HasError
   
   ok = False

   ComboBoxSer.Clear
   ComboBoxClient.Clear
   'ComboBoxGIP.Clear
   'ComboBoxAKM.Clear
   'ComboBoxSPD.Clear
   'ComboBoxGlSpec.Clear
   
   'заполняем комбобоксы из базы
   'запрос серий
   strSQL = "SELECT Имя FROM Серии ORDER BY Имя"
   objRec.Open Source:=strSQL, ActiveConnection:=objConect, _
                  CursorType:=adOpenKeyset, LockType:=adLockOptimistic, Options:=adCmdText
   If objRec.EOF And objRec.BOF Then
      'нет серий
   Else
      'заполняем комбобокс серий
      objRec.MoveFirst
      Do Until objRec.EOF
         ComboBoxSer.AddItem objRec!Имя
         objRec.MoveNext
      Loop
   End If
   objRec.Close
   'запрос заказчиков
   strSQL = "SELECT Название FROM Заказчики ORDER BY Название"
   objRec.Open Source:=strSQL, ActiveConnection:=objConect, _
               CursorType:=adOpenKeyset, LockType:=adLockOptimistic, Options:=adCmdText
   If objRec.EOF And objRec.BOF Then
      'нет Заказчиков
   Else
      'заполняем комбобокс заказчиков
      objRec.MoveFirst
      Do Until objRec.EOF
         ComboBoxClient.AddItem objRec!Название
         objRec.MoveNext
      Loop
   End If
   objRec.Close
   'запрос ГИПов
'   strSQL = "SELECT Фамилия FROM ГИПЫ ORDER BY Фамилия"
'   objRec.Open Source:=strSQL, ActiveConnection:=objConect, _
'               CursorType:=adOpenKeyset, LockType:=adLockOptimistic, Options:=adCmdText
'   If objRec.EOF And objRec.BOF Then
'      'нет ГИПов
'   Else
'      'заполняем комбобокс ГИПов
'      objRec.MoveFirst
'      Do Until objRec.EOF
'         ComboBoxGIP.AddItem objRec!Фамилия
'         objRec.MoveNext
'      Loop
'   End If
   
'   objRec.Close
'   'запрос Начальников АКМ
'   strSQL = "SELECT Фамилия FROM Нач_акм ORDER BY Фамилия"
'   objRec.Open Source:=strSQL, ActiveConnection:=objConect, _
'               CursorType:=adOpenKeyset, LockType:=adLockOptimistic, Options:=adCmdText
'   If objRec.EOF And objRec.BOF Then
'      'нет Начальников
'   Else
'      'заполняем комбобокс Начальников
'      objRec.MoveFirst
'      Do Until objRec.EOF
'         ComboBoxAKM.AddItem objRec!Фамилия
'         objRec.MoveNext
'      Loop
'   End If
'
'   objRec.Close
'   'запрос Начальников СПД
'   strSQL = "SELECT Фамилия FROM Нач_спд ORDER BY Фамилия"
'   objRec.Open Source:=strSQL, ActiveConnection:=objConect, _
'               CursorType:=adOpenKeyset, LockType:=adLockOptimistic, Options:=adCmdText
'   If objRec.EOF And objRec.BOF Then
'      'нет Начальников
'   Else
'      'заполняем комбобокс Начальников
'      objRec.MoveFirst
'      Do Until objRec.EOF
'         ComboBoxSPD.AddItem objRec!Фамилия
'         objRec.MoveNext
'      Loop
'   End If
'
'   objRec.Close
'   'запрос Гл.спецов
'   strSQL = "SELECT Фамилия FROM Гл_спецы ORDER BY Фамилия"
'   objRec.Open Source:=strSQL, ActiveConnection:=objConect, _
'               CursorType:=adOpenKeyset, LockType:=adLockOptimistic, Options:=adCmdText
'   If objRec.EOF And objRec.BOF Then
'      'нет Гл_спецы
'   Else
'      'заполняем комбобокс Гл_спецы
'      objRec.MoveFirst
'      Do Until objRec.EOF
'         ComboBoxGlSpec.AddItem objRec!Фамилия
'         objRec.MoveNext
'      Loop
'   End If
   
   Set objListItem = FormShifr.ListViewShifr.SelectedItem
   If objListItem Is Nothing Then Exit Sub
   'заполняем данные текущего выделенного шифра
   TextBoxShifr = objListItem.Text
   TextBoxBS = objListItem.SubItems(1)
   TextBoxPart = objListItem.SubItems(2)
   ComboBoxSer = objListItem.SubItems(3)
   TextBoxObjectName = objListItem.SubItems(4)
   TextBoxAdress = objListItem.SubItems(5)
   ComboBoxClient = objListItem.SubItems(6)
   TextBoxPost1 = objListItem.SubItems(7)
   TextBoxFam1 = objListItem.SubItems(8)
   TextBoxPost2 = objListItem.SubItems(9)
   TextBoxFam2 = objListItem.SubItems(10)
   TextBoxPost3 = objListItem.SubItems(11)
   TextBoxFam3 = objListItem.SubItems(12)
   TextBoxPost4 = objListItem.SubItems(13)
   TextBoxFam4 = objListItem.SubItems(14)
   TextBoxStage = objListItem.SubItems(15)
   
Exit Sub
HasError:
   If Err.Number = 94 Then Resume Next
   MsgBox Err.Description, vbCritical, psVBProjectName
   
End Sub

Private Sub UserForm_QueryClose(Cancel As Integer, CloseMode As Integer)
   
End Sub

Attribute VB_Name = "FormTitList"
Attribute VB_Base = "0{4C826BAE-DACD-4B62-99EF-21AB2B9595B5}{BDB1A289-FDEA-419E-8CAC-3422DE33C90C}"
Attribute VB_GlobalNameSpace = False
Attribute VB_Creatable = False
Attribute VB_PredeclaredId = True
Attribute VB_Exposed = False
Attribute VB_TemplateDerived = False
Attribute VB_Customizable = False
Option Explicit

Public objListItem As ListItem

Private Sub CheckBoxOsnKomplect_Click()
   
   If CheckBoxOsnKomplect.Value = True Then
      TextBoxShifr = objListItem & objListItem.SubItems(1) & "-" & objListItem.SubItems(2)
   Else
      TextBoxShifr = objListItem & "-" & objListItem.SubItems(2)
   End If
  
End Sub

Private Sub CheckBoxRow0_Click()
   ObrabCheckBoxRowClick CheckBoxRow0
End Sub

Private Sub CheckBoxRow1_Click()
   ObrabCheckBoxRowClick CheckBoxRow1
End Sub

Private Sub CheckBoxRow2_Click()
   ObrabCheckBoxRowClick CheckBoxRow2
End Sub

Private Sub CheckBoxRow3_Click()
   ObrabCheckBoxRowClick CheckBoxRow3
End Sub

Private Sub CheckBoxRow4_Click()
   ObrabCheckBoxRowClick CheckBoxRow4
End Sub

Private Sub cmbClose_Click()
  Hide
End Sub

Private Sub CreatTitList_Click()
  
  'вставка блоков обложек и заполнение атрибутов
  'блоки обложек из файла шаблона Обложки.dwg
  
  Me.Hide
  
  'копируем блоки обложек
  Dim sTitTemplate As String
  Dim sMacroFolder As String
  sMacroFolder = Functions.GetMacroFolder(psVBProjectName)
  sTitTemplate = sMacroFolder & "\Таблицы\Обложка.dwg"
  
  Dim doc As New AxDbDocument
  doc.Open sTitTemplate
  
  Dim objCol(0 To 3) As Object
  Dim vobj As Variant
   
  Set objCol(0) = doc.Blocks("Обложка_верх")
  Set objCol(1) = doc.Blocks("Обложка_низ")
  Set objCol(2) = doc.Blocks("Обложка_верх_А4")
  Set objCol(3) = doc.Blocks("Обложка_низ_А4")
  
  vobj = objCol
  
  doc.CopyObjects vobj, ThisDrawing.ModelSpace
  
  'вставка блоков
  Dim vPt As Variant
  Dim blRefTitVerh As AcadBlockReference
  Dim blRefTitNiz As AcadBlockReference
  vPt = ThisDrawing.Utility.GetPoint(, "Точка вставки обложек")
  
  Dim sBlNameVerh As String
  Dim sBlNameNiz As String
  
  If (OptionButtonA3.Value = True) Then
    sBlNameVerh = "Обложка_верх"
    sBlNameNiz = "Обложка_низ"
  Else
    sBlNameVerh = "Обложка_верх_А4"
    sBlNameNiz = "Обложка_низ_А4"
  End If
  
  Set blRefTitVerh = ThisDrawing.ModelSpace.InsertBlock(vPt, sBlNameVerh, 1, 1, 1, 0)
  vPt(0) = vPt(0) + 500
  Set blRefTitNiz = ThisDrawing.ModelSpace.InsertBlock(vPt, sBlNameNiz, 1, 1, 1, 0)
  
  'заполняем обложки
  ZapTitList blRefTitVerh, blRefTitNiz
  
  Me.Show
  
End Sub

Private Sub UserForm_Activate()
  'заполнение данных по шифру
  
  If objListItem Is Nothing Then Exit Sub
  
  If objListItem.SubItems(1) = "" Then
      CheckBoxOsnKomplect.Visible = False
   Else
      CheckBoxOsnKomplect.Visible = True
      CheckBoxOsnKomplect.Value = False
   End If
   
   TextBoxShifr = objListItem.Text & "-" & objListItem.SubItems(2)
   TextBoxClient = objListItem.SubItems(6)
   TextBoxAdress = objListItem.SubItems(5)
   TextBoxObjectName = objListItem.SubItems(4)
   TextBoxPost1 = objListItem.SubItems(7)
   TextBoxFam1 = objListItem.SubItems(8)
   TextBoxPost2 = objListItem.SubItems(9)
   TextBoxFam2 = objListItem.SubItems(10)
   TextBoxPost3 = objListItem.SubItems(11)
   TextBoxFam3 = objListItem.SubItems(12)
'   TextBoxPost4 = objListItem.SubItems(13)
'   TextBoxFam4 = objListItem.SubItems(14)
  
End Sub

Public Function ZapTitList(objBlVerhList As AcadBlockReference, objBlNigList As AcadBlockReference)
   'т.е заполняем обложки
   
   Dim objEntity As AcadEntity
   Dim objAtr As AcadAttributeReference
   Dim varAtr As Variant
   Dim objMS As AcadBlock
   

   Set objMS = ThisDrawing.ModelSpace
      
   'заполняем атрибуты верхней обложки
   If Not objBlVerhList Is Nothing Then
      For Each varAtr In objBlVerhList.GetAttributes
         Select Case VBA.LCase(varAtr.TagString)
            Case "шифр"
               varAtr.TextString = FormTitList.TextBoxShifr
            Case "наимен_объекта"
               varAtr.TextString = FormTitList.TextBoxObjectName
            Case "адрес"
               varAtr.TextString = FormTitList.TextBoxAdress
            Case "название_альбома"
               varAtr.TextString = FormTitList.ComboBoxAlbumName
            Case "год"
               varAtr.TextString = FormTitList.TextBoxYear
            Case "альбом_номер"
               varAtr.TextString = FormTitList.TextBoxAlbumNumber
         End Select
      Next
   End If
   
   Dim post(0 To 2) As String
   Dim fam(0 To 2) As String
   Dim i As Integer
   If CheckBoxRow0.Value = True Then
      post(i) = TextBoxPost0.Text
      fam(i) = TextBoxFam0.Text
      i = i + 1
   End If
   If CheckBoxRow1.Value = True Then
      post(i) = TextBoxPost1.Text
      fam(i) = TextBoxFam1.Text
      i = i + 1
   End If
   If CheckBoxRow2.Value = True Then
      post(i) = TextBoxPost2.Text
      fam(i) = TextBoxFam2.Text
      i = i + 1
   End If
   If CheckBoxRow3.Value = True Then
      post(i) = TextBoxPost3.Text
      fam(i) = TextBoxFam3.Text
      i = i + 1
   End If
   If CheckBoxRow4.Value = True Then
      post(i) = TextBoxPost4.Text
      fam(i) = TextBoxFam4.Text
      i = i + 1
   End If
   
   Dim val As String
   
   'заполняем атрибуты нижней обложки
   If Not objBlNigList Is Nothing Then
      For Each varAtr In objBlNigList.GetAttributes
         Select Case VBA.LCase(varAtr.TagString)
            Case "шифр"
               val = FormTitList.TextBoxShifr
            Case "наимен_объекта"
               val = FormTitList.TextBoxObjectName
            Case "адрес"
               val = FormTitList.TextBoxAdress
            Case "название_альбома"
               val = FormTitList.ComboBoxAlbumName
            Case "год"
               val = FormTitList.TextBoxYear
            Case "должность1"
               val = post(0)
            Case "фамилия1"
               val = fam(0)
            Case "должность2"
               val = post(1)
            Case "фамилия2"
               val = fam(1)
            Case "должность3"
               val = post(2)
            Case "фамилия3"
               val = fam(2)
            Case "альбом_номер"
               val = FormTitList.TextBoxAlbumNumber
         End Select
         If val = "" Then
            varAtr.TextString = ""
         Else
            varAtr.TextString = val
         End If
      Next
   End If
   
End Function

Private Sub UserForm_Initialize()
  
  'Заполнение комбобокса наименований альбомов
  ComboBoxAlbumName.AddItem "Наружные стеновые панели"
  ComboBoxAlbumName.AddItem "Внутренние стеновые панели"
  ComboBoxAlbumName.AddItem "Плиты перекрытия"
  ComboBoxAlbumName.AddItem "Доборные изделия"
  ComboBoxAlbumName.AddItem "Изделия чердака"
  ComboBoxAlbumName.AddItem "Арматурные и закладные изделия"
  ComboBoxAlbumName.AddItem "Сборные железобетонные изделия"
  ComboBoxAlbumName.AddItem "Арматурные изделия ростверка"
  
End Sub

Private Function ObrabCheckBoxRowClick(cb As CheckBox)
   'Не более трех галок могут быть активны для рядов должностей и фамилий.
   
   If cb.Value = False Then Exit Function
   
   Dim count As Integer
   
   If CheckBoxRow0.Value = True Then count = 1
   If CheckBoxRow1.Value = True Then count = count + 1
   If CheckBoxRow2.Value = True Then count = count + 1
   If CheckBoxRow3.Value = True Then count = count + 1
   If CheckBoxRow4.Value = True Then count = count + 1
   
   If count > 3 Then
      cb.Value = False
      MsgBox "Для обложки возможно только три должности."
   End If
   
End Function

Attribute VB_Name = "Functions"
Option Explicit


'Public Function GetColShifFromTXT(ShifrTXTFullPath As String) As Collection
'   'считываем строки из файла и заполняем коллекцию объектами шифра
'
'   Dim colShifr As New Collection
'   Dim objShifr As clShifr
'   Dim strShifr As String
'   Dim strValue As String
'   Dim intValue As Integer
'
'   'форма записы шифра:
'   '3085-10;Купряхин А.П.;ЗАО"Кронверк-3";Шурова Гора 7, в Ленинском районе г.Саратова;Жилой дом №10
'
'   If Dir(ShifrTXTFullPath) = "" Then
'      'возвращаем Nothing
'      Exit Function
'   End If
'
'   Close #1
'   'через открытие файла
'   Open ShifrTXTFullPath For Input Access Read As #1
'   'чтение файла
'   While Not EOF(1)
'      Set objShifr = New clShifr
'      Line Input #1, strShifr
'      'до первого ; - шифр
'      intValue = InStr(strShifr, ";")
'      strValue = Left(strShifr, intValue - 1)
'      objShifr.Shifr = strValue
'      strShifr = Mid(strShifr, intValue + 1) 'сокращаем строчку до первого ; включительно
'      'до второго ; - (бс)
'      intValue = InStr(strShifr, ";")
'      strValue = Left(strShifr, intValue - 1)
'      objShifr.BS = strValue
'      strShifr = Mid(strShifr, intValue + 1)
'      'до след ; - часть
'      intValue = InStr(strShifr, ";")
'      strValue = Left(strShifr, intValue - 1)
'      objShifr.Part = strValue
'      strShifr = Mid(strShifr, intValue + 1)
'      'до след ; - ГИП
'      intValue = InStr(strShifr, ";")
'      strValue = Left(strShifr, intValue - 1)
'      objShifr.GIP = strValue
'      strShifr = Mid(strShifr, intValue + 1)
'      'след ; - заказчик
'      intValue = InStr(strShifr, ";")
'      strValue = Left(strShifr, intValue - 1)
'      objShifr.Clients = strValue
'      strShifr = Mid(strShifr, intValue + 1)
'      'след ; - адресс
'      intValue = InStr(strShifr, ";")
'      strValue = Left(strShifr, intValue - 1)
'      objShifr.Adress = strValue
'      strShifr = Mid(strShifr, intValue + 1)
'      'след ; - наименование объекта
'      intValue = InStr(strShifr, ";")
'      strValue = Left(strShifr, intValue - 1)
'      objShifr.ObjectName = strValue
'      strShifr = Mid(strShifr, intValue + 1)
'      'след ; - должность нач.отдела
'      intValue = InStr(strShifr, ";")
'      strValue = Left(strShifr, intValue - 1)
'      objShifr.FieldNachOtd = strValue
'      strShifr = Mid(strShifr, intValue + 1)
'      'след ;  - фамилия нач.отдела
'      intValue = InStr(strShifr, ";")
'      strValue = Left(strShifr, intValue - 1)
'      objShifr.FamNachOtd = strValue
'      strShifr = Mid(strShifr, intValue + 1)
'      'след фамилия Гл.специалиста
'      objShifr.GlSpec = strShifr
'      'добавляем объект в коллекцию
'      colShifr.Add objShifr, objShifr.Shifr
'   Wend
'   Close #1
'
'   Set GetColShifFromTXT = colShifr
'
'End Function
'
'Public Function GetColGIPFromTXT(GIPTxtFullPath As String) As Collection
'   'считываем гипов из файла
'   'заполняем массив из типов по гипавм
'
'   Dim colGIP As New Collection
'   Dim objGIP As clGIP
'   Dim strGIP As String
'   Dim intValue As Integer
'
'   'форма записы ГИПа:
'   'Купряхин С.П.
'
'   If Dir(GIPTxtFullPath) = "" Then
'      'возвращаем Nothing
'      Exit Function
'   End If
'
'   Close #1
'   'открываем файл для чтения
'   Open GIPTxtFullPath For Input Access Read As #1
'   'чтение файла
'   While Not EOF(1)
'      Set objGIP = New clShifr
'      Line Input #1, strGIP
'      'пока только одна запись в строчке - Фамилия И.О.
'      objGIP.FamilIO = strGIP
'      'добавляем объект в коллекцию
'      'проверка на ошибку совпадении ключей, при добавлении нового гипа в коллекцию ?????????
'      colGIP.Add objGIP, objGIP.FamilIO
'   Wend
'   Close #1
'
'   Set GetColGIPFromTXT = colGIP
'
'End Function
'
'Public Function GetColClientFromTXT(ClientTxtFullPath As String) As Collection
'   'считываем заказчиков из файла
'   'заполняем массив из типов по заказчикам
'
'   Dim colClient As New Collection
'   Dim objClient As clClient
'   Dim strClient As String
'   Dim intValue As Integer
'
'   'форма записы заказчика:
'   'ЗАО"Кронверк-3"
'
'   If Dir(ClientTxtFullPath) = "" Then
'      'возвращаем Nothing
'      Exit Function
'   End If
'
'   Close #1
'   'открываем файл для чтения
'   Open ClientTxtFullPath For Input Access Read As #1
'   'чтение файла
'   While Not EOF(1)
'      Set objClient = New clClient
'      Line Input #1, strClient
'      'пока только одна запись в строчке - название фирмы
'      objClient.Firma = strClient
'      'добавляем объект в коллекцию
'      'проверка на ошибку совпадении ключей, при добавлении нового заказчика в коллекцию ?????????
'      colClient.Add objClient, objClient.Firma
'   Wend
'   Close #1
'
'   Set GetColClientFromTXT = colClient
'
'End Function

'Public Function AddShifrToList(objShifr As clShifr) As Boolean
'   ' добавление шифра в листбокс
'
'   Dim objListItem As ListItem
'
'   On Error GoTo HasError
'
'   If objShifr Is Nothing Then
'      AddShifrToList = False
'      Exit Function
'   End If
'
'   Set objListItem = FormShifr.ListViewShifr.ListItems.Add(, objShifr.Shifr, objShifr.Shifr)
'   objListItem.SubItems(1) = objShifr.BS
'   objListItem.SubItems(2) = objShifr.Part
'   objListItem.SubItems(3) = objShifr.GIP
'   objListItem.SubItems(4) = objShifr.Clients
'   objListItem.SubItems(5) = objShifr.Adress
'   objListItem.SubItems(6) = objShifr.ObjectName
'   objListItem.SubItems(7) = objShifr.FieldNachOtd
'   objListItem.SubItems(8) = objShifr.FamNachOtd
'   objListItem.SubItems(9) = objShifr.GlSpec
'
'   AddShifrToList = True
'
'Exit Function
'
'HasError:
'   Select Case Err.Number
'      Case "-2145386476" 'Ключ не найден'Case "Key is not unique in collection"
'         AddShifrToList = False
'         Exit Function
'      Case Else
'         MsgBox "Функция - AddShifrToList" & vbCrLf & _
'               Err.Description, vbCritical, psVBProjectName
'   End Select
'
'End Function

Public Function GetShifrFromDict() As String
   'чтение записи шифра из словаря
   'словарь SPD
   'запись Shifr
   'если нет словаря или записи, возвращает ""
   
   Dim objDict As AcadDictionary
   Dim objXRec As AcadXRecord
   Dim XRDataType As Variant
   Dim XRDataValue As Variant
   
   On Error GoTo HasError
   
   'получаем словарь чертежа
   Set objDict = ThisDrawing.Dictionaries.Item("SPD")
   'получаем запись SPD из словаря
   Set objXRec = objDict.Item("Shifr")
   'считываем данные записи
   objXRec.GetXRecordData XRDataType, XRDataValue
   
   If IsEmpty(XRDataValue) = True Then
      GetShifrFromDict = ""
      Exit Function
   Else
      GetShifrFromDict = XRDataValue(0)
      Exit Function
   End If

Exit Function

'обработка шибок
HasError:
   Select Case Err.Number
      Case "-2145386476" 'Ключ не найден
         'если нет записи
         'возвращаем пустую строчку
'         MsgBox "Ключ не найден"
         GetShifrFromDict = ""
         Exit Function
      Case Else
         MsgBox "Функция GetShifrFromDict - " & Err.Description, vbCritical, psVBProjectName
         GetShifrFromDict = ""
         Exit Function
   End Select
   
Resume Next
   
End Function

Public Function SetShifrToDict(strShifr As String) As Boolean
   'запись шифра в словарь
   'словарь SPD
   'запись Shifr
   
   Dim objDict As AcadDictionary
   Dim objXRec As AcadXRecord
   Dim XRDataType(0) As Integer
   Dim XRDataValue(0) As Variant
   
   On Error GoTo HasError
   
   'получаем словарь
   Set objDict = ThisDrawing.Dictionaries.Item("SPD")
   If objDict Is Nothing Then
      'нет словаря в чертеже, создаем
      Set objDict = ThisDrawing.Dictionaries.Add("SPD")
   End If
   
   Set objXRec = objDict.Item("Shifr")
   If objXRec Is Nothing Then
      'если нет записы, создаем
      Set objXRec = objDict.AddXRecord("Shifr")
   End If
   
   XRDataType(0) = 1
   XRDataValue(0) = strShifr
    
   'записываем в XRecord словаря
   objXRec.SetXRecordData XRDataType, XRDataValue
   
   SetShifrToDict = True

Exit Function

HasError:
   Select Case Err.Number
      Case "-2145386476" 'Ключ не найден
         'если словаря или записи, продолжаем, там далее идет создание
         Resume Next
      Case Else
         MsgBox "Err.Description - " & Err.Description, vbCritical, psVBProjectName
         SetShifrToDict = False
         Exit Function
   End Select
     
End Function

Public Function GetColBlockName(strBlockName As String) As Collection
   'возвращает коллекцию блоков заданного имиени в черткеже
   
   Dim selBlocks As AcadSelectionSet
   Dim objBlockRef As AcadBlockReference
   Dim intFT(1) As Integer
   Dim varFD(1) As Variant
   
   'создаем набор
   Set selBlocks = GetNewSelSet("Блоки")
   
   'задаем фильтр
   intFT(0) = 0: varFD(0) = "insert"
   intFT(1) = 2: varFD(1) = strBlockName
   
   selBlocks.Select acSelectionSetAll, , , intFT, varFD
   
   If selBlocks.count = 0 Then
      Set GetColBlockName = Nothing
   Else
      Set GetColBlockName = New Collection
      For Each objBlockRef In selBlocks
         GetColBlockName.Add objBlockRef
      Next
   End If
   
End Function

Public Function GetNewSelSet(strSelName As String) As AcadSelectionSet
   'возвращает набор, с заданным именем
   'если набор с таким именем был, он очищается
   
   Dim selSet As AcadSelectionSet
   
   For Each selSet In ThisDrawing.SelectionSets
      If selSet.Name = strSelName Then
         selSet.Clear
         Set GetNewSelSet = selSet
         Exit Function
      End If
   Next
   
   Set GetNewSelSet = ThisDrawing.SelectionSets.Add(strSelName)
   
End Function

Public Function GetFamilWithoutInitial(strFamil As String) As String
   'возвращает строку фамилии без инициалов
   'разделителем фамилии и инициалов может быть или " " или прописная буква
   
   Dim intLen As Integer
   Dim strSymbol As String
   Dim i As Integer
   
   On Error Resume Next
   
   intLen = InStr(strFamil, " ")
   
   'если есть пробел, то значит это пробел между фамилией и инициалами
   If intLen <> 0 Then
      GetFamilWithoutInitial = VBA.Left(strFamil, intLen - 1)
   Else
      GetFamilWithoutInitial = strFamil
   End If
   
End Function

Public Function CheckAccessToShifrTxt() As String
   'проверка редактирется ли каталог шифров сейчас
   'определяется наличием файла "Shifr_Edit.txt", рядом с основным txt
   'возвращает имя компа - если база редактруется сейчас
   'или "" если доступ свободен
   
   Dim strShifrEditTxt As String
   
   On Error GoTo HasError
   
   strShifrEditTxt = GetMacroFolder(psVBProjectName) & "\Shifr_Edit.txt"
   'проверяем наличие файла "Shifr_Edit.txt"
   If Dir(strShifrEditTxt) = "" Then
      CheckAccessToShifrTxt = ""
   Else
      'определяем имя компа, т.е. считываем первую строчку
      'открываем файл для чтения
      Open strShifrEditTxt For Input Access Read As #2
      'считываем первую строчку
      Line Input #2, CheckAccessToShifrTxt
      'закрываем файл
      Close #2
   End If

Exit Function
HasError:
   MsgBox Err.Description, vbCritical, psVBProjectName
   
End Function

Public Function OpenAccessToShifrTxtYesNo() As Boolean
   'создаем скрытый файл, только для чтения "Shifr_Edit.txt"
   
   Dim strShifrEditTxt As String
   Dim strKompName As String
   
   On Error GoTo HasError
   
   'имя этого компъютера в сети
   strKompName = WinAPI.ComputerName
   
   'файл для создания
   strShifrEditTxt = GetMacroFolder(psVBProjectName) & "\Shifr_Edit.txt"
   'открываем скрытый файл для записи
   Open strShifrEditTxt For Output Lock Write As #2
      Print #2, strKompName
   Close #2
   
   OpenAccessToShifrTxtYesNo = True

Exit Function
HasError:
   MsgBox Err.Description, vbCritical, psVBProjectName
   
End Function

Public Function GetMacroFolder(psVBProjectName) As String
   'получение пути к корню макроса
   'без \
   
   Dim strMacroFolder As String
   Dim intValue As Integer
   
   On Error GoTo HasError
   
   strMacroFolder = Application.VBE.vbprojects.Item(psVBProjectName).FileName
   intValue = InStrRev(strMacroFolder, "\")
   strMacroFolder = VBA.Left(strMacroFolder, intValue - 1) 'корень с макросом, без \ на конце
   
   GetMacroFolder = strMacroFolder
   
Exit Function

HasError:
   Select Case Err.Number
      Case Else
         MsgBox "Functions, GetMacroFolder" & vbCrLf & _
               Err.Description, vbCritical, psVBProjectName
   End Select
   
End Function

Public Function AddBlocksFromDWG(strDwgFileFullPath) As Boolean
   'внедрение определений блоков из внешнего файла в текущий чертеж
   
   Dim dPt(2) As Double
   Dim objXref As AcadExternalReference
   Dim strValue As String
   Dim intValue As Integer
   
   On Error Resume Next
   
   'проверяем существование указанного файла
   If Dir(strDwgFileFullPath) = "" Then
      AddBlocksFromDWG = False
      Exit Function
   End If
   'проверка имени текущего чертежа и вставляемого
   If ThisDrawing.FullName <> strDwgFileFullPath Then
      'вставляем ссылку
      Set objXref = ThisDrawing.ModelSpace.AttachExternalReference(strDwgFileFullPath, "Name_", dPt, 1, 1, 1, 0, False)
      ThisDrawing.Blocks.Item(objXref.Name).Bind True
      objXref.Delete
      ThisDrawing.Blocks.Item("Name_").Delete
   End If
   
   AddBlocksFromDWG = True
   
End Function


Public Function FindShifrsToListViev(sShifr As String)
   'поиск по шифру и вывод списка в ListViev
   
   Dim strSQL As String
   Dim objListItem As ListItem
   Dim vMark As Variant
   
   On Error GoTo HasError
   
   'запрос шифров
   If objRecSet.State = adStateOpen Then objRecSet.Close
   objRecSet.Filter = adFilterNone
   
   If FormShifr.ComboBoxFilterSer = "" Or FormShifr.ComboBoxFilterSer = "Все" Then
      strSQL = "SELECT * FROM Шифры ORDER BY Шифры.Дата_создания"
         
      'strSQL = "SELECT Шифры.Шифр, Шифры.БС, Шифры.Часть, Шифры.Серия, Шифры.Адрес, Шифры.Наимен_объекта, Шифры.ГИП, Шифры.Заказчик, Шифры.Нач_отд,Шифры.Отд,  Шифры.Гл_спец " & _
         "FROM Серии INNER JOIN (Нач_отд INNER JOIN (Заказчики INNER JOIN (Гл_спецы INNER JOIN (ГИПЫ INNER JOIN Шифры ON ГИПЫ.Фамилия = Шифры.ГИП) ON Гл_спецы.Фамилия = Шифры.Гл_спец) ON Заказчики.Название = Шифры.Заказчик) ON Нач_отд.Фамилия = Шифры.Нач_отд) ON Серии.Имя = Шифры.Серия " & _
         "ORDER BY Шифры.Шифр"
   Else
      strSQL = "SELECT * FROM Шифры " & _
               "WHERE Шифры.Серия = '" & FormShifr.ComboBoxFilterSer & "' " & _
               "ORDER BY Шифры.Дата_создания"
      'strSQL = "SELECT Шифры.Шифр, Шифры.БС, Шифры.Часть, Шифры.Серия, Шифры.Адрес, Шифры.Наимен_объекта, Шифры.ГИП, Шифры.Заказчик, Шифры.Нач_отд,Шифры.Отд,  Шифры.Гл_спец " & _
         "FROM Серии INNER JOIN (Нач_отд INNER JOIN (Заказчики INNER JOIN (Гл_спецы INNER JOIN (ГИПЫ INNER JOIN Шифры ON ГИПЫ.Фамилия = Шифры.ГИП) ON Гл_спецы.Фамилия = Шифры.Гл_спец) ON Заказчики.Название = Шифры.Заказчик) ON Нач_отд.Фамилия = Шифры.Нач_отд) ON Серии.Имя = Шифры.Серия " & _
         "WHERE Шифры.Серия = '" & FormShifr.ComboBoxFilterSer & "' " & _
         "ORDER BY Шифры.Шифр"
   End If
   
   objRecSet.Open Source:=strSQL, ActiveConnection:=objConect, _
               CursorType:=adOpenKeyset, LockType:=adLockOptimistic, Options:=adCmdText
   If objRecSet.EOF And objRecSet.BOF Then
      MsgBox "Нет шифров в катологе!", vbExclamation, psVBProjectName
      Exit Function
   End If
   
   objRecSet.MoveFirst
   'поиск записи
   objRecSet.Find "Шифр like '" & sShifr & "*'"
   'если найдено, то очищаем список листвиевера
'   If Not objRecSet.EOF Then
      FormShifr.ListViewShifr.ListItems.Clear
'   End If
   Do While Not objRecSet.EOF
      Set objListItem = FormShifr.ListViewShifr.ListItems.Add(, , objRecSet!Шифр)
      objListItem.SubItems(1) = objRecSet!БС
      objListItem.SubItems(2) = objRecSet!Часть
      objListItem.SubItems(3) = objRecSet!Серия
      objListItem.SubItems(4) = objRecSet!Наимен_объекта
      objListItem.SubItems(5) = objRecSet!Адрес
      objListItem.SubItems(6) = objRecSet!Заказчик
      objListItem.SubItems(7) = objRecSet!Должность1
      objListItem.SubItems(8) = objRecSet!Фамилия1
      objListItem.SubItems(9) = objRecSet!Должность2
      objListItem.SubItems(10) = objRecSet!Фамилия2
      objListItem.SubItems(11) = objRecSet!Должность3
      objListItem.SubItems(12) = objRecSet!Фамилия3
      objListItem.SubItems(13) = objRecSet!Должность4
      objListItem.SubItems(14) = objRecSet!Фамилия4
      objListItem.SubItems(15) = objRecSet!Стадия
      objListItem.SubItems(16) = objRecSet!Дата_создания
      
      vMark = objRecSet.Bookmark
      objRecSet.Find "Шифр like '" & sShifr & "*'", 1, adSearchForward, vMark
   Loop
      
Exit Function
HasError:
   If Err.Number = 94 Then
      Resume Next
   End If
   MsgBox Err.Description, vbCritical, psVBProjectName
   
End Function

Public Function SetUserFamily(sFamely As String)
   'запись фамилии юзера(по имени компьютера SPD-26)
   
   Dim oUserIni As New ClassINI
   Dim sMacroFolder As String
   Dim sUserName As String 'имя пользователя
   
   On Error GoTo HasError
   
   'определение имени пользоваттеля
   sUserName = WinAPI.ComputerName
   
   'определяем ини файл
   sMacroFolder = GetMacroFolder(psVBProjectName)
   
   oUserIni.CreateIni "User.ini", sMacroFolder & "\Ini"
   
   oUserIni.WriteFile "User", sUserName, sFamely

Exit Function
HasError:
   MsgBox Err.Description, vbCritical, psVBProjectName
   
End Function

Public Function GetUserFamily() As String
   'определение фамилии юзера(по имени компьютера SPD-26) из ини файла User.ini
   
   Dim oUserIni As New ClassINI
   Dim sMacroFolder As String
   Dim sUserName As String 'имя пользователя
   
   On Error GoTo HasError
   
   'определение имени пользоваттеля
   sUserName = WinAPI.ComputerName
   
   'определяем ини файл
   sMacroFolder = GetMacroFolder(psVBProjectName)
   
   oUserIni.CreateIni "User.ini", sMacroFolder & "\Ini"
   
   GetUserFamily = oUserIni.GetFile("User", sUserName)

Exit Function
HasError:
   MsgBox Err.Description, vbCritical, psVBProjectName
   
End Function

Public Function GetLayer(strLayer As String) As AcadLayer
   Dim objLayer As AcadLayer
   
   On Error GoTo HasError
   Set GetLayer = ThisDrawing.Layers.Item(strLayer)
   
Exit Function
HasError:
   Set GetLayer = ThisDrawing.Layers.Add(strLayer)
End Function


Public Function RedefineBlock(file As String, blockName As String)
   'Переопределение блока в текщем чертеже блоком из файла
   'используется библиотека ObjectDBX 17 (её нужно подключить в референсах), для скрытого открытия файла dwg
   'для переопределения блоко - заменяются все объекты в блоке
   'для дин.блоков может не будет работать, не пробовал.
   
   On Error GoTo HasError
   'открыть файл источник
   Dim docSource As New AXDBLib.AxDbDocument
   Dim blSource As AcadBlock
   Dim objs(0) As Object
   docSource.Open file
   Set blSource = docSource.Blocks.Item(blockName)
   Set objs(0) = blSource
   
   'Проверка существования блока в текущем чертеже
   Dim blTarget As AcadBlock
   On Error Resume Next
   Set blTarget = ThisDrawing.Blocks.Item(blockName)
   If blTarget Is Nothing Then
      'если в текущем чертеже нет этого блока, тогда просто можно скопировать его
      docSource.CopyObjects objs, ThisDrawing.Blocks
      Exit Function
   End If
   
   'если блок есть в текущем чертеже, тогда нужно переопределить его.
   'для этого можно заменить все объекты в блоке
   On Error GoTo HasError
   
   Dim objEnts() As Object
   ReDim objEnts(0 To blSource.count - 1)
   Dim i As Integer
   'выбираем все объекты блока источника
   For i = 0 To blSource.count - 1
      Set objEnts(i) = blSource(i)
   Next
   'удаляем все объекты из целевого блока
   While blTarget.count > 0
      blTarget(0).Delete
   Wend
   'копируем объекты в целевой блок
   docSource.CopyObjects objEnts, blTarget
   
   Exit Function
HasError:
   MsgBox Err.Description, vbCritical, psVBProjectName
End Function

Public Function ZamenaBlockaStampa(blRef As AcadBlockReference) As AcadBlockReference
   'замена вхождения блока штампа с сохранением значений атрибутов
   'присвоение нового блока blRef ??? изменится ли ссылка в колекции??
   
   'разморозка, разблокировка и включение слоя блока
   Dim layer As AcadLayer
   Set layer = ThisDrawing.Layers(blRef.layer)
   If layer.Freeze = True Then layer.Freeze = False
   If layer.Lock = True Then layer.Lock = False
   If layer.LayerOn = False Then layer.LayerOn = True
   
   'вставка блока
   Dim blRefNew As AcadBlockReference
   Dim space As AcadBlock
   Set space = ThisDrawing.ObjectIdToObject(blRef.OwnerID)
   Set blRefNew = space.InsertBlock(blRef.InsertionPoint, blRef.Name, blRef.XScaleFactor, _
                                    blRef.YScaleFactor, blRef.ZScaleFactor, blRef.Rotation)
   Set ZamenaBlockaStampa = blRefNew
   'копирование свойств блока
   blRefNew.layer = blRef.layer
   blRefNew.Linetype = blRef.Linetype
   blRefNew.Lineweight = blRef.Lineweight
   blRefNew.color = blRef.color
   
   'копирование значения атрибута НАИМЕНОВАНИЕ чертежа
   If blRef.HasAttributes And blRefNew.HasAttributes Then

      Dim vAttsSource As Variant
      vAttsSource = blRef.GetAttributes
      Dim vAttsTarget As Variant
      vAttsTarget = blRefNew.GetAttributes

      Dim attSource As AcadAttributeReference
      Dim attTarget As AcadAttributeReference
      
      Set attTarget = FindAtt("НАИМЕНОВАНИЕ", vAttsTarget)
      Set attSource = FindAtt("НАИМЕНОВАНИЕ", vAttsSource)
      If Not attTarget Is Nothing And Not attSource Is Nothing Then
         attTarget.TextString = attSource.TextString
         attTarget.ScaleFactor = attSource.ScaleFactor
      End If
      Set attTarget = FindAtt("ЛИСТ", vAttsTarget)
      Set attSource = FindAtt("ЛИСТ", vAttsSource)
      If Not attTarget Is Nothing And Not attSource Is Nothing Then
         attTarget.TextString = attSource.TextString
         attTarget.ScaleFactor = attSource.ScaleFactor
      End If
      Set attTarget = FindAtt("ЛИСТОВ", vAttsTarget)
      Set attSource = FindAtt("ЛИСТОВ", vAttsSource)
      If Not attTarget Is Nothing And Not attSource Is Nothing Then
         attTarget.TextString = attSource.TextString
         attTarget.ScaleFactor = attSource.ScaleFactor
      End If
   End If

   'копирование значений атрибутов
'   If blRef.HasAttributes And blRefNew.HasAttributes Then
'
'      Dim vAttsSource As Variant
'      vAttsSource = blRef.GetAttributes
'      Dim vAttsTarget As Variant
'      vAttsTarget = blRefNew.GetAttributes
'
'      Dim attSource As AcadAttributeReference
'      Dim attTarget As AcadAttributeReference
'      Dim attFound As Boolean
'      Dim sTag As String
'      Dim vobj As Variant
'      Dim vobj2 As Variant
'      For Each vobj In vAttsSource
'         Set attSource = vobj
'         attFound = False
'         For Each vobj2 In vAttsTarget
'            Set attTarget = vobj2
'            If UCase(attSource.TagString) = UCase(attTarget.TagString) Then
'               attFound = True
'               Exit For
'            End If
'         Next
'         If attFound = False Then
'            sTag = ""
'            Select Case UCase(attSource.TagString)
'               Case "ГИП"
'                  sTag = "ДОЛЖНОСТЬ1"
'               Case "ФАМГИП"
'                  sTag = "ФАМИЛИЯ1"
'               Case "НАЧАКМ"
'                  sTag = "ДОЛЖНОСТЬ2"
'               Case "ФАМНАЧАКМ"
'                  sTag = "ФАМИЛИЯ2"
'               Case "НАЧСПД"
'                  sTag = "ДОЛЖНОСТЬ3"
'               Case "ФАМНАЧСПД"
'                  sTag = "ФАМИЛИЯ3"
'               Case "ГЛСПЕЦ"
'                  sTag = "ДОЛЖНОСТЬ4"
'               Case "ФАМГЛСПЕЦ"
'                  sTag = "ФАМИЛИЯ4"
'               Case "ИНЖ"
'                  sTag = "ДОЛЖНОСТЬ5"
'               Case "ФАМИНЖ"
'                  sTag = "ФАМИЛИЯ5"
'               Case "ИНЖ2"
'                  sTag = "ДОЛЖНОСТЬ6"
'               Case "ФАМИНЖ2"
'                  sTag = "ФАМИЛИЯ6"
'            End Select
'            If sTag <> "" Then
'               Set attTarget = FindAtt(sTag, vAttsTarget)
'               If Not attTarget Is Nothing Then
'                  attFound = True
'               End If
'            End If
'         End If
'         If attFound Then
'            attTarget.TextString = attSource.TextString
'            attTarget.ScaleFactor = attSource.ScaleFactor
'         End If
'      Next
'   End If
   
   blRef.Delete
   
End Function

Public Function FindAtt(sTag As String, vAtts As Variant) As AcadAttributeReference
   Dim att As Variant
   For Each att In vAtts
      If VBA.UCase(att.TagString) = sTag Then
         Set FindAtt = att
         Exit For
      End If
   Next
End Function

Attribute VB_Name = "Main"
'************ САРАТОВГРАЖДАНПРОЕКТ СПД 2008 ****************************************************
'
'******************* Каталог Шифров ****************************
'---------------------------------------------------------------
' Ведение каталога шифров проектов, по данным из карточкек.
' Данные сохраняются в тесктовом файле, в корне с макросом
' Шифр для чертежей сохраняется в словаре "SPD", запись 0 (1 . Shifr as string)
' --------------------------------------------------------------
'Доп.процедуры(на кнопки):
'InsStamp - вставка блока штампа, по данным из каталога шифров
'InsScheme - вставка блока компановочной схемы, файла в корне проекта, с
'            названием "Компановка + Шифр.dwg"
'
' ограничение кол-ва шифров - integer, т.е. 32627
' помоему больше и быть не может
' можно увеличить до long, но тогда уж лучше переходить на СУБД
   
Option Explicit
   
   Public objRecSet As New ADODB.Recordset
   Public objRecShifr As New ADODB.Recordset
   Public objConect As New ADODB.Connection
   Public Const strProvider As String = "Provider=Microsoft.Jet.OLEDB.4.0;"
   
   Public Const psVBProjectName As String = "SPD_SHIFR"
   Public bolBaseWriteRead As Boolean
   Public bolIzm As Boolean
   
Public Sub Shifrs()
   'просмотр и редактирование базы шифров проектов
   
   'очищаем форму
   Set FormShifr = Nothing
   
   'форма для редактирования шифров
   'в не модально режиме, с возможностью переключения чертежей и назначения им шфров
   FormShifr.Show ' vbModeless
   
End Sub

Public Sub InsStamp()
   'процедура вставки бока штампа
   
'   Dim colShifr As Collection
'   Dim objShifr As clShifr
   Dim strMacroPath As String
   Dim strShifr As String
   Dim strSQL As String
   Dim strConect As String
   
   On Error GoTo HasError
   
   'считываем запись "Sfifr" из словаря "SPD"
   'если его нет, запрос заполнения шифра для текущего чертежа из коллекции шифров
   strShifr = Functions.GetShifrFromDict
   If strShifr = "" Then
      MsgBox "Этому чертежу не был назначен шифр.", vbInformation, psVBProjectName
'      'передаем все дальнейшие управления в форму
'      FormInsStamp1.Show
'      Exit Sub
'      FormShifr.Show  'процедура работа с каталогом шифров
'      strShifr = Functions.GetShifrFromDict
'      If strShifr = "" Then
'         MsgBox "Шифр небыл назначен. Выход."
'         Exit Sub
'      End If
'      Exit Sub
   End If
   
   'получение корня макроса
   strMacroPath = Functions.GetMacroFolder(psVBProjectName)
      
   'процедура заполнения коллекции шифров из текстового файла
'   Set colShifr = Functions.GetColShifFromTXT(strMacroPath & "\Shifr.txt")
   'запрос шифра из базы
   If objConect.State = adStateOpen Then
      'подключение уже открыто
'      objConect.Close
   Else
      'строка подключения
      strConect = strProvider & _
               "Data Source=" & strMacroPath & "\Базы\Шифры.mdb"
      'подключение
      objConect.CursorLocation = adUseClient
      objConect.Mode = adModeWrite  'дугие смогут тоже подключатьься
      objConect.Open strConect
   End If
   
   If strShifr = "" Then
      FormInsStamp1.Show
      Exit Sub
   End If
   
   'запрос шифров
   If objRecShifr.State = adStateOpen Then objRecShifr.Close
   strSQL = "SELECT * FROM Шифры WHERE Шифр = '" & strShifr & "'"
   objRecShifr.Open Source:=strSQL, ActiveConnection:=objConect, _
                  CursorType:=adOpenKeyset, LockType:=adLockOptimistic, Options:=adCmdText
   If objRecShifr.EOF And objRecShifr.BOF Then
      MsgBox "Не найден шифр в катологе!", vbExclamation, psVBProjectName
      objRecShifr.Close
      FormInsStamp1.Show
      Exit Sub
   End If
   
'   'находим нужный шифр в коллеции шифров colShifr
'   'если его нет, запрос заполнить данные для шифра
'   Set objShifr = colShifr.Item(strShifr)
'   If objShifr Is Nothing Then
'      MsgBox "Шифра чертежа - " & strShifr & vbCrLf & _
'             "Нет в каталоге шифров."
'      Shifrs 'процедура работа с каталогом шифров
'      Exit Sub
'   End If
   
   'заполняем форму FormInsStamp
   FormInsStamp1.TextBoxShifr = objRecShifr!Шифр & "-" & objRecShifr!Часть
   FormInsStamp1.TextBoxClient = objRecShifr!Заказчик
   FormInsStamp1.TextBoxAdress = objRecShifr!Адрес
   FormInsStamp1.TextBoxNomerDoma = objRecShifr!Наимен_объекта
   FormInsStamp1.TextBoxPost1 = objRecShifr!Должность1
   FormInsStamp1.TextBoxPost2 = objRecShifr!Должность2
   FormInsStamp1.TextBoxPost3 = objRecShifr!Должность3
   FormInsStamp1.TextBoxPost4 = objRecShifr!Должность4
   FormInsStamp1.TextBoxPost5 = "Инженер"
   FormInsStamp1.TextBoxFam1 = Functions.GetFamilWithoutInitial(objRecShifr!Фамилия1)
   FormInsStamp1.TextBoxFam2 = Functions.GetFamilWithoutInitial(objRecShifr!Фамилия2)
   FormInsStamp1.TextBoxFam3 = Functions.GetFamilWithoutInitial(objRecShifr!Фамилия3)
   FormInsStamp1.TextBoxFam4 = Functions.GetFamilWithoutInitial(objRecShifr!Фамилия4)
   'определяем фамилию пользователя1
   FormInsStamp1.TextBoxFam5 = Functions.GetUserFamily
   FormInsStamp1.TextBoxStage = objRecShifr!Стадия
   
   'передаем все дальнейшие управления в форму
   FormInsStamp1.Show

Exit Sub

HasError:
   Select Case Err.Number
      Case 94
         Resume Next
      Case -2145386476 'Ключ не найден
         Resume Next
      Case 5 ' "Invalid procedure call or argument"
         Resume Next
      Case Else
         MsgBox Err.Description, vbCritical, psVBProjectName
         Exit Sub
   End Select
   
End Sub

'Public Sub InsScheme()
'   'процедура вставки бока компановочной схемы
'
'   'считываем запись "Шифр" из словаря "СПД"
'   'если его нет, запрос заполнения шифра для текущего чертежа из коллекции шифров
'
'   'процедура заполнения коллекции шифров из текстового файла
'
'   'находим нужный шифр в коллеции шифров colShifr
'   'если его нет, запрос заполнить данные для шифра
'
'   'заполняем форму FormInsStamp
'
'   'вставка блока из файла заготовки штампа с атрибутами
'
'   'выставление масштаба блоку
'
'   'заполнение атрибутов
'
'End Sub

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Option Explicit



Public Sub space()
  Dim vList As Variant
  If ThisDrawing.ActiveSpace = acModelSpace Then
    vList = ThisDrawing.ActiveSpace
  Else
  
  End If
  
End Sub

Attribute VB_Name = "WinAPI"
Option Explicit

Private Declare Function GetComputerName Lib "kernel32" Alias "GetComputerNameA" (ByVal lpBuffer As String, nSize As Long) As Long
Private Declare Function GetUserName Lib "advapi32.dll" Alias "GetUserNameA" _
        (ByVal lpBuffer As String, nSize As Long) As Long


'функции получения имени компьютера и имени пользователя
'v_1.0.0 990630
Public Function ComputerName() As String
   Dim a As String * 40
   Dim nSize As Long
   nSize = 40
   Call GetComputerName(a, nSize)
   ComputerName = StrZ(a)
End Function
'v_1.0.0 990831
Public Function UserName() As String
Dim a As String * 40
Dim nSize As Long
nSize = 40
   Call GetUserName(a, nSize)
   UserName = StrZ(a)
End Function
'v_1.0.0 990630
Private Function StrZ(par As String) As String
Dim nSize As Long, i As Long, Rez As String
   nSize = Len(par)
   i = InStr(1, par, VBA.Chr(0)) - 1
   If i > nSize Then i = nSize
   If i < 0 Then i = nSize
   StrZ = VBA.Mid(par, 1, i)
End Function

Attribute VB_Name = "clShifr"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
   
   Dim strShifr As String
   Dim strClients As String
   Dim strAdress As String
   Dim strObjectName As String
   Dim strBS As String
   Dim strPart As String
   Dim sPost1 As String
   Dim sPost2 As String
   Dim sPost3 As String
   Dim sPost4 As String
   Dim sFam1 As String
   Dim sFam2 As String
   Dim sFam3 As String
   Dim sFam4 As String
   Dim sStage As String
   Dim dateCreate As DataObject

'шифр: например "3085-10"
Public Property Get Shifr() As String
   Shifr = strShifr
End Property
Public Property Let Shifr(ByVal strValue As String)
   strShifr = strValue
End Property

'(бс) - перечень б.с. - (А-К)
Public Property Get BS() As String
   BS = strBS
End Property
Public Property Let BS(ByVal strValue As String)
   strBS = strValue
End Property

'часть - АС
Public Property Get Part() As String
   Part = strPart
End Property
Public Property Let Part(ByVal strValue As String)
   strPart = strValue
End Property

'название фирмы заказчика : ООО"Кронверк-3"
Public Property Get Clients() As String
   Clients = strClients
End Property
Public Property Let Clients(ByVal strValue As String)
   strClients = strValue
End Property

'адресс объекта
Public Property Get Adress() As String
   Adress = strAdress
End Property
Public Property Let Adress(ByVal strValue As String)
   strAdress = strValue
End Property

'Наименование здания : Жилой дом №10
Public Property Get ObjectName() As String
   ObjectName = strObjectName
End Property
Public Property Let ObjectName(ByVal strValue As String)
   strObjectName = strValue
End Property

'должность1
Public Property Get post1() As String
   post1 = sPost1
End Property
Public Property Let post1(ByVal strValue As String)
   sPost1 = strValue
End Property

'должность2
Public Property Get post2() As String
   post2 = sPost2
End Property
Public Property Let post2(ByVal strValue As String)
   sPost2 = strValue
End Property

'должность3
Public Property Get post3() As String
   post3 = sPost3
End Property
Public Property Let post3(ByVal strValue As String)
   sPost3 = strValue
End Property

'должность4
Public Property Get Post4() As String
   Post4 = sPost1
End Property
Public Property Let Post4(ByVal strValue As String)
   sPost4 = strValue
End Property

'фамилия 1
Public Property Get fam1() As String
   fam1 = sFam1
End Property
Public Property Let fam1(ByVal strValue As String)
   sFam1 = strValue
End Property

'фамилия 2
Public Property Get fam2() As String
   fam2 = sFam2
End Property
Public Property Let fam2(ByVal strValue As String)
   sFam2 = strValue
End Property

'фамилия 3
Public Property Get fam3() As String
   fam3 = sFam3
End Property
Public Property Let fam3(ByVal strValue As String)
   sFam3 = strValue
End Property

'фамилия 4
Public Property Get Fam4() As String
   Fam4 = sFam4
End Property
Public Property Let Fam4(ByVal strValue As String)
   sFam4 = strValue
End Property

'Стадия
Public Property Get Stage() As String
   Stage = sStage
End Property
Public Property Let Stage(ByVal strValue As String)
   sStage = strValue
End Property

'Дата создания
Public Property Get DateCreation() As Date
   DateCreation = dateCreate
End Property
Public Property Let DateCreation(ByVal Value As Date)
   dateCreate = Value
End Property
