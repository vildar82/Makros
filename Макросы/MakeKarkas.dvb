Attribute VB_Name = "BadMarkaKBl"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public sError As String
Public oBlRef As AcadBlockReference

Attribute VB_Name = "BlockAndMarkaK"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public oBl As AcadBlockReference
Public sMarkaK As String
Public sType As String
Public iNumK As Integer
Public sAtrMarka As String

Attribute VB_Name = "BrowseFolder"
Option Explicit

Declare Function GetDC Lib "user32" (ByVal hwnd As Long) As Long
Declare Function ReleaseDC Lib "user32" (ByVal hwnd As Long, _
  ByVal hDC As Long) As Long
Declare Function GetDeviceCaps Lib "gdi32" (ByVal hDC As Long, _
  ByVal nIndex As Long) As Long

Const HWND_DESKTOP As Long = 0
Const LOGPIXELSX As Long = 88
Const LOGPIXELSY As Long = 90
Const HORZRES As Long = 8
Const VERTRES As Long = 10


Public Type RECT
    Left As Long
    Top As Long
    Right As Long
    Bottom As Long
End Type

Public Declare Function MoveWindow Lib "user32.dll" ( _
     ByVal hwnd As Long, _
     ByVal X As Long, _
     ByVal Y As Long, _
     ByVal nWidth As Long, _
     ByVal nHeight As Long, _
     ByVal bRepaint As Long) As Long

Public Declare Function GetWindowRect Lib "user32.dll" ( _
     ByVal hwnd As Long, _
     lpRect As RECT) As Long

Public Declare Function WaitForInputIdle Lib "user32" ( _
    ByVal hProcess As Long, _
    ByVal dwMilliseconds As Long) As Long

Public Declare Function FindWindowEx Lib "user32.dll" Alias "FindWindowExA" ( _
     ByVal hWnd1 As Long, _
     ByVal hWnd2 As Long, _
     ByVal lpsz1 As String, _
     ByVal lpsz2 As String) As Long

Public Declare Function EnumThreadWindows Lib "user32" _
    (ByVal dwThreadId As Long, _
    ByVal lpfn As Long, _
    ByVal lParam As Long) As Long

Public Declare Function GetWindowThreadProcessId Lib "user32.dll" ( _
     ByVal hwnd As Long, _
     lpdwProcessId As Long) As Long

Public Declare Function SetWindowPos Lib "user32.dll" ( _
     ByVal hwnd As Long, _
     ByVal hWndInsertAfter As Long, _
     ByVal X As Long, _
     ByVal Y As Long, _
     ByVal cx As Long, _
     ByVal cy As Long, _
     ByVal wFlags As Long) As Long

Public Declare Function SetWindowText Lib "user32.dll" Alias "SetWindowTextA" ( _
     ByVal hwnd As Long, _
     ByVal lpString As String) As Long

Public Const SWP_SHOWWINDOW = &H40
Public Const HWND_TOPMOST = -1

Public g_CurrentDirectory As String
Public g_FileMasks() As String
Public g_ChangeSize As Boolean
Public g_DialogTitle As String
Public g_RatioX As Double, g_RatioY As Double
Public g_CenterOnScreen As Boolean
Public g_TopMost As Boolean

Public g_newLeft As Long, g_newTop As Long
Public g_deltaH As Long, g_deltaW As Long

Public Const WM_USER As Long = &H400
Public Const BFFM_INITIALIZED = 1
Public Const BFFM_SELCHANGED = 2
Public Const BFFM_SETSTATUSTEXT = (WM_USER + 100)
Public Const BFFM_ENABLEOK = (WM_USER + 101)
Public Const BFFM_SETSELECTION = (WM_USER + 102)

Public Type BrowseInfo
    hWndOwner As Long
    pIDLRoot As Long
    pszDisplayName As Long
    lpszTitle As Long
    ulFlags As Long
    lpfnCallback As Long
    lParam As Long
    iImage As Long
End Type

Public Enum WhatBrowse
    BIF_RETURNONLYFSDIRS = &H1
    BIF_BROWSEINCLUDEFILES = &H1 Or &H4000
    BIF_BROWSEFORCOMPUTER = &H1000
    BIF_BROWSEFORPRINTER = &H2000
    BIF_DONTGOBELOWDOMAIN = &H2
    BIF_STATUSTEXT = &H4
    BIF_NEWDIALOGSTYLE = &H40
    BIF_EDITBOX = &H10
    BIF_USENEWUI = (BIF_NEWDIALOGSTYLE Or BIF_EDITBOX)
    BIF_RETURNFSANCESTORS = &H8
End Enum

Public Const MAX_PATH = 260&
Public Declare Function SendMessage Lib "user32" Alias "SendMessageA" _
  (ByVal hwnd As Long, _
   ByVal wMsg As Long, _
   ByVal wParam As Long, _
   lParam As Any) As Long
Public Declare Sub CoTaskMemFree Lib "ole32.dll" (ByVal hMem As Long)
Public Declare Function lstrcat Lib "kernel32" Alias "lstrcatA" _
    (ByVal lpString1 As String, _
    ByVal lpString2 As String) As Long
Public Declare Function SHBrowseForFolder Lib "shell32" (lpbi As BrowseInfo) As Long
Public Declare Function SHGetPathFromIDList Lib "shell32" _
    (ByVal pidList As Long, _
    ByVal lpBuffer As String) As Long

Public Function fBrowseForFolder(ByVal hWnd_Owner As Long, _
                                 ByVal sPrompt As String, _
                                 ByVal WhatBr As Long, _
                                 ByVal DialogTitle As String, _
                                 Optional ByVal initDir As String = "", _
                                 Optional ByRef fileMasks As String = "", _
                                 Optional ByVal ChangeSize As Boolean = False, _
                                 Optional ByVal RatioX As Double = 1, _
                                 Optional ByVal RatioY As Double = 1, _
                                 Optional ByVal CenterOnScreen As Boolean = False, _
                                 Optional ByVal PromptColor As Long = 0&, _
                                 Optional ByVal PathColor As Long = 0&, _
                                 Optional ByVal TopMost As Boolean) As String

    Dim iNull As Integer
    Dim lpIDList As Long
    Dim lResult As Long
    Dim sPath As String
    Dim udtBI As BrowseInfo

    g_DialogTitle = DialogTitle
    g_ChangeSize = ChangeSize
    g_RatioX = RatioX
    g_RatioY = RatioY
    g_CenterOnScreen = CenterOnScreen
    g_TopMost = TopMost

    If initDir = "" Then
        g_CurrentDirectory = ""
    Else
        g_CurrentDirectory = initDir & vbNullChar
    End If

    If fileMasks = "" Then
        ReDim g_FileMasks(0 To 0)
        g_FileMasks(0) = ""
    Else
        g_FileMasks = Split(fileMasks, "|")
    End If

    With udtBI
        .hWndOwner = hWnd_Owner
        .lpszTitle = lstrcat(sPrompt, "")
        .ulFlags = WhatBr
        .lpfnCallback = GetAddressofFunction(AddressOf BrowseCallbackProc)  'get address of function.
    End With
    lpIDList = SHBrowseForFolder(udtBI)

    If lpIDList Then
        sPath = String$(MAX_PATH, 0)
        lResult = SHGetPathFromIDList(lpIDList, sPath)
        Call CoTaskMemFree(lpIDList)
        iNull = InStr(sPath, vbNullChar)
        If iNull Then sPath = Left$(sPath, iNull - 1)
    End If
    fBrowseForFolder = sPath

End Function

Public Function BrowseCallbackProc(ByVal hwnd As Long, ByVal uMsg As Long, ByVal lp As Long, ByVal pData As Long) As Long

    Dim lpIDList As Long
    Dim ret As Long
    Dim sBuffer As String
    Dim i As Integer, flag As Boolean, sPath As String

    On Error Resume Next

    Select Case uMsg

        Case BFFM_INITIALIZED
            If g_CurrentDirectory <> "" Then
                Call SendMessage(hwnd, BFFM_SETSELECTION, 1, ByVal g_CurrentDirectory)
            End If

            SetWindowText hwnd, g_DialogTitle
            If g_ChangeSize Then
                Call ResizeDialog(hwnd)

            Else
                If g_CenterOnScreen Then Call CenterDialog(hwnd)
            End If

        Case BFFM_SELCHANGED
            sBuffer = Space$(MAX_PATH)

            ret = SHGetPathFromIDList(lp, sBuffer)
            If ret = 1 Then
                Call SendMessage(hwnd, BFFM_SETSTATUSTEXT, 0, ByVal sBuffer)
                If g_FileMasks(0) <> "" Then
                    sPath = Left$(sBuffer, InStr(1, sBuffer, vbNullChar) - 1)
                    If Right$(sPath, 1) <> "\" Then sPath = sPath + "\"
                    flag = False
                    For i = 0 To UBound(g_FileMasks)
                        If Dir(sPath + g_FileMasks(i)) <> "" Then flag = True
                    Next i
                    If flag Then
                        Call SendMessage(hwnd, BFFM_ENABLEOK, 0, ByVal 1&)
                    Else
                        Call SendMessage(hwnd, BFFM_ENABLEOK, 0, ByVal 0&)
                    End If
                End If
            End If

        Case Else
    End Select

    BrowseCallbackProc = 0

End Function

Public Function GetAddressofFunction(add As Long) As Long
    GetAddressofFunction = add
End Function

Private Sub ResizeDialog(ByVal hwnd As Long)
    Dim pid As Long, thread_id As Long
    Dim screenWidth As Long, screenHeight As Long
    Dim winWidth As Long, winHeight As Long
    Dim R As RECT
    Dim lngDC As Long
    Dim lWidth As Long
    Dim lHeight As Long
    
    lngDC = GetDC(HWND_DESKTOP)
    screenWidth = GetDeviceCaps(lngDC, HORZRES)
    screenHeight = GetDeviceCaps(lngDC, VERTRES)
    
    GetWindowRect hwnd, R

    winWidth = (R.Right - R.Left) * g_RatioX
    winHeight = (R.Bottom - R.Top) * g_RatioY
    g_deltaH = winHeight - (R.Bottom - R.Top)
    g_deltaW = winWidth - (R.Right - R.Left)

    If g_CenterOnScreen Then
        g_newLeft = (screenWidth - winWidth) / 2
        g_newTop = (screenHeight - winHeight) / 2
    Else
        g_newLeft = R.Left
        g_newTop = R.Top
    End If

    If g_TopMost Then
        SetWindowPos hwnd, HWND_TOPMOST, g_newLeft, g_newTop, winWidth, winHeight, SWP_SHOWWINDOW
    Else
        SetWindowPos hwnd, 0, g_newLeft, g_newTop, winWidth, winHeight, SWP_SHOWWINDOW
    End If

    thread_id = GetWindowThreadProcessId(hwnd, pid)
    Call WaitForInputIdle(pid, 1000&)
    EnumThreadWindows thread_id, AddressOf EnumThreadWndProc, 0&

End Sub

'--------------------------------------------------
Function TwipsPerPixelX() As Single
'--------------------------------------------------
'Returns the width of a pixel, in twips.
'--------------------------------------------------
  Dim lngDC As Long
  lngDC = GetDC(HWND_DESKTOP)
  TwipsPerPixelX = 1440& / GetDeviceCaps(lngDC, LOGPIXELSX)
  ReleaseDC HWND_DESKTOP, lngDC
End Function

'--------------------------------------------------
Function TwipsPerPixelY() As Single
'--------------------------------------------------
'Returns the height of a pixel, in twips.
'--------------------------------------------------
  Dim lngDC As Long
  lngDC = GetDC(HWND_DESKTOP)
  TwipsPerPixelY = 1440& / GetDeviceCaps(lngDC, LOGPIXELSY)
  ReleaseDC HWND_DESKTOP, lngDC
End Function

Public Function EnumThreadWndProc(ByVal hwnd As Long, ByVal lParam As Long) As Long
    Dim treeHwnd As Long, okButtonHwnd As Long, cancelButtonHwnd As Long, promptHwnd As Long, folderHwnd As Long
    Dim R As RECT
    Static allControlsAdjusted As Integer

    okButtonHwnd = FindWindowEx(hwnd, ByVal 0&, "Button", vbNullString)
    If okButtonHwnd <> 0 Then
        GetWindowRect okButtonHwnd, R
        MoveWindow okButtonHwnd, (R.Left - g_newLeft - 3) + g_deltaW, (R.Top - g_newTop - 22) + g_deltaH, R.Right - R.Left, R.Bottom - R.Top, 1
        allControlsAdjusted = allControlsAdjusted + 10000
        cancelButtonHwnd = FindWindowEx(hwnd, okButtonHwnd, "Button", vbNullString)
        If cancelButtonHwnd <> 0 Then
            GetWindowRect cancelButtonHwnd, R
            MoveWindow cancelButtonHwnd, (R.Left - g_newLeft - 3) + g_deltaW, (R.Top - g_newTop - 22) + g_deltaH, R.Right - R.Left, R.Bottom - R.Top, 1
            allControlsAdjusted = allControlsAdjusted + 1000
        End If
    End If

    treeHwnd = FindWindowEx(hwnd, ByVal 0&, "SysTreeView32", vbNullString)
    If treeHwnd <> 0 Then
        GetWindowRect treeHwnd, R
        MoveWindow treeHwnd, R.Left - g_newLeft - 3, R.Top - g_newTop - 22, (R.Right - R.Left) + g_deltaW, (R.Bottom - R.Top) + g_deltaH, 1
        allControlsAdjusted = allControlsAdjusted + 100
    End If

    promptHwnd = FindWindowEx(hwnd, ByVal 0&, "Static", vbNullString)
    If promptHwnd <> 0 Then
        GetWindowRect promptHwnd, R
        MoveWindow promptHwnd, R.Left - g_newLeft - 3, R.Top - g_newTop - 22, (R.Right - R.Left) + g_deltaW, R.Bottom - R.Top, 1
        allControlsAdjusted = allControlsAdjusted + 10
        folderHwnd = FindWindowEx(hwnd, promptHwnd, "Static", vbNullString)
        If folderHwnd <> 0 Then
            GetWindowRect folderHwnd, R
            MoveWindow folderHwnd, R.Left - g_newLeft - 3, R.Top - g_newTop - 22, (R.Right - R.Left) + g_deltaW, R.Bottom - R.Top, 1
            allControlsAdjusted = allControlsAdjusted + 1
        End If
    End If

    EnumThreadWndProc = Not (allControlsAdjusted = 11111)
End Function

Private Sub CenterDialog(ByVal hwnd As Long)
    Dim screenWidth As Long, screenHeight As Long
    Dim winWidth As Long, winHeight As Long
    Dim R As RECT
    Dim lngDC As Long
    Dim lWidth As Long
    Dim lHeight As Long

    lngDC = GetDC(HWND_DESKTOP)
    screenWidth = GetDeviceCaps(lngDC, HORZRES)
    screenHeight = GetDeviceCaps(lngDC, VERTRES)

    GetWindowRect hwnd, R

    winWidth = (R.Right - R.Left)
    winHeight = (R.Bottom - R.Top)

    g_newLeft = (screenWidth - winWidth) / 2
    g_newTop = (screenHeight - winHeight) / 2

    SetWindowPos hwnd, 0, g_newLeft, g_newTop, winWidth, winHeight, SWP_SHOWWINDOW
End Sub


Public Sub Тест_выбор_папки()
   
   Dim st As String
   Dim lngDC As Long
   
   lngDC = GetDC(HWND_DESKTOP)
   
    st = fBrowseForFolder(0&, _
                          "Внимание: вложенные папки не учиываются." & vbCrLf & _
                                    "Поэтому выбирайте каждый каталог по отдельности." & vbCrLf & _
                                    "Можно выбрать только папку содержащую файлы dwg!", _
                          BIF_RETURNONLYFSDIRS, _
                          "Выберите папку c блоками", _
                          "\\Sgpsrv2\спд\Конструкторы\Пан. Кронверк( 17 эт.)\От архитекторов 2.10.08", _
                          "*.DWG*", _
                          True, _
                          1, _
                          1, _
                          True, _
                          0, _
                          0, _
                          True)
    If Len(st) > 0 Then MsgBox "Вы выбрали папку:" + vbCr + st, vbInformation, "Информация"
   
End Sub

Attribute VB_Name = "ClassINI"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
 
Private strInI As String
 
'// Win API Declares
Private Declare Function WritePrivateProfileString _
  Lib "kernel32" Alias "WritePrivateProfileStringA" _
 (ByVal lpApplicationName As String, _
  ByVal lpKeyName As Any, _
  ByVal lpString As Any, _
  ByVal lpFileName As String) As Long
 
Private Declare Function GetPrivateProfileString _
  Lib "kernel32" Alias "GetPrivateProfileStringA" _
 (ByVal lpApplicationName As String, _
  ByVal lpKeyName As Any, _
  ByVal lpDefault As String, _
  ByVal lpReturnedString As String, _
  ByVal nSize As Long, _
  ByVal lpFileName As String) As Long
 
Private Function MakePath(ByVal strFileName As String, _
  ByVal strPath As String) As String
 
 '// Makes an INI file: Guarantees a sub dir
 Do While Right$(strPath, 1) = "\"
   strPath = Left$(strPath, Len(strPath) - 1)
 Loop
 
 Do While Left$(strFileName, 1) = "\"
   strFileName = Mid$(strFileName, 2)
 Loop
 
 '// Return the path
 MakePath = strPath & "\" & strFileName
End Function
 
Public Sub CreateIni(strFileName As String, strPath As String)
 '// Make a new ini file
 strInI = MakePath(strFileName, strPath)
End Sub
 
Public Sub WriteFile(strSection As String, _
 strKey As String, _
 strValue As String)
 
 '// Write to strINI
 WritePrivateProfileString strSection, _
   strKey, strValue, strInI
End Sub
 
Public Function GetFile(strSection As String, _
  strKey As String) As String
 
  Dim strTmp As String
  Dim lngRet As String
 
  strTmp = String$(100, 0)
  lngRet = GetPrivateProfileString(strSection, _
    strKey, "", strTmp, _
    Len(strTmp), strInI)
 
  GetFile = StrZ(strTmp)
 
End Function
 
Public Property Let INIFile(ByVal New_IniPath As String)
   'Устанавливаем путь к файлу ini
   strInI = New_IniPath
End Property
Public Property Get INIFile() As String
   INIFile = strInI
End Property
 
 
'v_1.0.0 990630
Private Function StrZ(par As String) As String
Dim nSize As Long, i As Long, Rez As String
   nSize = Len(par)
   i = InStr(1, par, Chr(0)) - 1
   If i > nSize Then i = nSize
   If i < 0 Then i = nSize
   StrZ = Mid(par, 1, i)
End Function

Attribute VB_Name = "FormBadBlMarkaK"
Attribute VB_Base = "0{B8549478-7D0A-462E-89CA-74FCB14378D9}{3B90A3DD-BA37-4568-8D08-33601EE3D86A}"
Attribute VB_GlobalNameSpace = False
Attribute VB_Creatable = False
Attribute VB_PredeclaredId = True
Attribute VB_Exposed = False
Attribute VB_TemplateDerived = False
Attribute VB_Customizable = False
Option Explicit

Private Sub cmbOK_Click()
  End
End Sub

Private Sub cmbView_Click()
  Dim index As Integer
  
  On Error GoTo HasError

  index = ListBoxBlocks.ListIndex
  If index = -1 Then
    Exit Sub
  End If
  
  Dim oBadMarkaK As BadMarkaKBl
  Dim oBlRef As AcadBlockReference
  Dim vMin As Variant
  Dim vMax As Variant
  
  Set oBadMarkaK = pcolBadMarkaKBl(ListBoxBlocks.List(index, 1))
  
  oBadMarkaK.oBlRef.Highlight True
  
  oBadMarkaK.oBlRef.GetBoundingBox vMin, vMax
  ZoomWindow vMin, vMax
Exit Sub
HasError:
  If Err.Number = -2145386420 Then 'если блок был удален
    MsgBox "Блок был удален", vbExclamation, psVBProjectName
    'удаляем из коллекции
    pcolBadMarkaKBl.Remove ListBoxBlocks.List(index, 1)
    'удаляем его из листбокса
    ListBoxBlocks.RemoveItem index
  Else
    MsgBox Err.Description, vbCritical, psVBProjectName
  End If
End Sub

Private Sub ListBoxBlocks_Click()
  
  Dim index As Integer

  index = ListBoxBlocks.ListIndex
  If index = -1 Then
    Exit Sub
  End If
  
  Dim oBadMarkaK As BadMarkaKBl
  
  Set oBadMarkaK = pcolBadMarkaKBl(ListBoxBlocks.List(index, 1))
  
  TextBoxError = oBadMarkaK.sError
  
End Sub

Private Sub UserForm_Initialize()

  Dim oBadBlMarkaK As BadMarkaKBl
  'вывод списка блоков
  For Each oBadBlMarkaK In pcolBadMarkaKBl
    ListBoxBlocks.AddItem oBadBlMarkaK.oBlRef.Name, 0
    ListBoxBlocks.List(0, 1) = oBadBlMarkaK.oBlRef.ObjectID
  Next
End Sub

Attribute VB_Name = "FormMain"
Attribute VB_Base = "0{98A5F946-C74C-4FC0-B441-AA89A9CA3B1D}{B0A646ED-912A-4C45-B4D6-67F25B1C22EF}"
Attribute VB_GlobalNameSpace = False
Attribute VB_Creatable = False
Attribute VB_PredeclaredId = True
Attribute VB_Exposed = False
Attribute VB_TemplateDerived = False
Attribute VB_Customizable = False
Option Explicit
   
   Public objKar As New clKarkas 'параметры текущего каркаса
   Dim colBlName As New Collection
   Dim msBiblPath As String
   
   Dim typeFiles() As FileBlock 'массив имен файлов и имен папок в библиотеке
   
   Const msFileIniName = psVBProjectName & ".ini"
   
   Const msSection As String = "MakeBlockKarkasa"
   Const msKeyBiblPath As String = "BiblPath"
   
   Dim intLeft As Integer
   Dim intTop As Integer
   
Private Sub CheckBoxD_Click()
  OprMarky
End Sub

Public Sub CheckBoxKR_Click()
'  'открываем поля марок К
'  If CheckBoxKR.Value = True Then
'    Label1K.Visible = True
'    TextBoxMarkaK.Visible = True
'    TextBoxNomerK.Visible = True
'    'выводим список каркасов в этом чертеже
'    SetBlockToListFromDrawing
'
'    'заполняем комбобоксы хвостов
'    ComboBoxHvostLeft.Clear
'    ComboBoxHvostLeft.AddItem FormOptions.TextBoxHvostK0, 0
'    ComboBoxHvostLeft.AddItem FormOptions.TextBoxHvostK1, 1
'    ComboBoxHvostLeft.AddItem FormOptions.TextBoxHvostK2, 2
'    ComboBoxHvostLeft.AddItem FormOptions.TextBoxHvostK3, 3
'    ComboBoxHvostLeft.AddItem FormOptions.TextBoxHvostK4, 4
'    ComboBoxHvostLeft.AddItem FormOptions.TextBoxHvostK5, 5
'    ComboBoxHvostLeft.AddItem FormOptions.TextBoxHvostK6, 6
'    ComboBoxHvostLeft.AddItem FormOptions.TextBoxHvostK7, 7
'    ComboBoxHvostLeft.AddItem FormOptions.TextBoxHvostK8, 8
'    ComboBoxHvostLeft.AddItem FormOptions.TextBoxHvostK9, 9
'    ComboBoxHvostLeft.AddItem 20, 10
'    ComboBoxHvostRight.Clear
'    ComboBoxHvostRight.List = ComboBoxHvostLeft.List
'  Else
'    Label1K.Visible = False
'    TextBoxMarkaK.Visible = False
'    TextBoxNomerK.Visible = False
'    SetBlocksFromBiblToArray
'    'заполняем комбобоксы хвостов
'    ComboBoxHvostLeft.Clear
'    ComboBoxHvostLeft.AddItem FormOptions.TextBoxHvost0, 0
'    ComboBoxHvostLeft.AddItem FormOptions.TextBoxHvost1, 1
'    ComboBoxHvostLeft.AddItem FormOptions.TextBoxHvost2, 2
'    ComboBoxHvostLeft.AddItem FormOptions.TextBoxHvost3, 3
'    ComboBoxHvostLeft.AddItem FormOptions.TextBoxHvost4, 4
'    ComboBoxHvostLeft.AddItem FormOptions.TextBoxHvost5, 5
'    ComboBoxHvostLeft.AddItem FormOptions.TextBoxHvost6, 6
'    ComboBoxHvostLeft.AddItem FormOptions.TextBoxHvost7, 7
'    ComboBoxHvostLeft.AddItem FormOptions.TextBoxHvost8, 8
'    ComboBoxHvostLeft.AddItem FormOptions.TextBoxHvost9, 9
'    ComboBoxHvostLeft.AddItem 20, 10
'    ComboBoxHvostRight.Clear
'    ComboBoxHvostRight.List = ComboBoxHvostLeft.List
'  End If
'
End Sub

Private Sub cmbBibl_Click()
   'выбор папки библиотеки блоков каркасов

   Dim strPathDefault As String
   Dim strDefaultPath As String
   Dim sBiblPathVal As String
   Dim i As Integer
   
   On Error Resume Next
   
   If msBiblPath = "" Then
      strDefaultPath = CurDir
   Else
      strDefaultPath = msBiblPath
   End If
   
   'открываем диалог выбора папок
   sBiblPathVal = fBrowseForFolder(hWnd_Owner:=0&, _
                        sPrompt:="", _
                        WhatBr:=BIF_RETURNONLYFSDIRS Or BIF_STATUSTEXT, _
                        DialogTitle:="Выбор библиотеки блоков каркасов", _
                        initDir:=strDefaultPath, _
                        fileMasks:="", _
                        ChangeSize:=True, _
                        RatioX:=1, _
                        RatioY:=1, _
                        CenterOnScreen:=True, _
                        TopMost:=True)
   If sBiblPathVal = "" Then
'    msBiblPath = ""
'    TextBoxBibl = ""
    Exit Sub
  End If
   
   msBiblPath = sBiblPathVal
   
   'записываем путь библиотеки в ини
   FileIni.WriteFile msSection, msKeyBiblPath, msBiblPath
   
   'вывод списка блоков из библиотеки в листбокс
   SetBlocksFromBiblToArray
   'заполнение комбобокса фильтра по кол П, и комбобокс фильтра по типуК
    AddKolPToCombo
   
   TextBoxBibl = msBiblPath
    
End Sub

Private Sub cmbDel_Click()
   'удалить блок из библиотеки
   Dim index As Integer
   
   On Error GoTo HasError
   
   index = ListBoxBlocks.ListIndex
   If index = -1 Then Exit Sub
  
  If bolKirp = False Then
   If MsgBox("Удалить блок " & ListBoxBlocks & " из библиотеки", vbQuestion + vbYesNo, psVBProjectName) = vbNo Then Exit Sub
   
   Dim sFileKarkas As String
   sFileKarkas = msBiblPath & "\" & ListBoxBlocks.List(index, 1) & "\" & ListBoxBlocks & ".dwg"
   
   On Error Resume Next
   Kill sFileKarkas
   If Err Then
      MsgBox "Не удалось удалить файл - " & sFileKarkas
      Err.Clear
   End If
   
  Else
    Dim oBl As AcadBlock
    Dim oBlRef As AcadBlockReference
    Dim selSet As AcadSelectionSet
    Dim colK As Collection
    Dim oNumKandPlos As Num_PlosName
    Dim iCode(1) As Integer
    Dim vDate(1) As Variant
    Dim bolYes As Boolean
    'запрос удаления
    If MsgBox("Удалить блок " & ListBoxBlocks, vbQuestion + vbYesNo, psVBProjectName) = vbNo Then Exit Sub
  
    'удаляем определение блока блока
    On Error Resume Next
      For Each oBl In ThisDrawing.Blocks
        If oBl.Name = ListBoxBlocks Then
          oBl.Delete
          bolYes = True
        End If
      Next
      If bolYes = False Then
        MsgBox "Определенрие блока не найдено", vbCritical, psVBProjectName
        Exit Sub
      End If
      If Err Then
        Err.Clear
        'значит есть вхождения блока
        'запрос удаления вхождений блоков
        Set selSet = Functions.GetSelSet("Блоки")
        iCode(0) = 0: vDate(0) = "insert"
        iCode(1) = 2: vDate(1) = ListBoxBlocks
        selSet.Select acSelectionSetAll, , , iCode, vDate
        If MsgBox("Найдено " & selSet.Count & " блоков на чертеже. Удалить их?", vbExclamation + vbYesNo, psVBProjectName) = vbNo Then Exit Sub
        selSet.Erase
        For Each oBl In ThisDrawing.Blocks
          If oBl.Name = ListBoxBlocks Then
            oBl.Delete
          End If
        Next
        If Err Then
          MsgBox "Удалить определение блока не удалось", vbCritical, psVBProjectName
          Exit Sub
        End If
      End If
    On Error GoTo 0
  End If
  
  'удаление номераК из коллекции
    Select Case objKar.strType
      Case "КД"
        Set colK = pcolPlosNumKD
      Case "КО"
        Set colK = pcolPlosNumKO
      Case "К"
        Set colK = pcolPlosNumK
    End Select
    Err.Clear
    On Error Resume Next
    Set oNumKandPlos = colK(objKar.strPlosKarName)
    If Err Then
      Err.Clear
     ' MsgBox "Не удалось удалить номерК из коллекции номеров"
     'вообще нет номера
      Exit Sub
    End If
    'если не осталось блоков в колекции блоков с этим номером, то удаляем объект номераК из коллекции
    bolYes = False
    For Each oBlRef In oNumKandPlos.colBl
      If oBlRef.Name <> "" Then
        If Err Then
          'блок был удален
          'oNumKandPlos.colBl.Remove oBlRef
        Else
          bolYes = True
        End If
      End If
    Next
    On Error GoTo 0
    If bolYes = False Then
      'удаляем объект из коллекции номеровК
      colK.Remove oNumKandPlos.sPlosKar
    End If
   ListBoxBlocks.RemoveItem index
   
Exit Sub
HasError:
   MsgBox Err.Description, vbCritical, psVBProjectName
End Sub

Private Sub cmbExit_Click()
  End
End Sub

Private Sub cmbExplorer_Click()
'(startapp "explorer.exe" (strcat "/n,/e," "\\\\Sgpsrv2\\СПД\\Конструкторы\\Елена\\Библиотека по кирпичке\\Жемчужина\\"))
'(startapp "explorer.exe" (strcat "/n,/e," (getvar "dwgprefix")))
  Dim sComm As String
  Dim sBiblPath As String
  
  Me.hide
  
  sBiblPath = TextBoxBibl
  If sBiblPath <> "" Then
    sBiblPath = Replace(sBiblPath, "\", "\\") & "\\"
    'Shell sBiblPath
  End If

  sComm = "(startapp " & Chr(34) & "explorer" & Chr(46) & "exe" & Chr(34) & _
  " (strcat " & Chr(34) & "/n,/e," & Chr(34) & "  " & Chr(34) & sBiblPath & Chr(34) & "))(princ)"
  ThisDrawing.SendCommand sComm & vbCr
  
End Sub

Private Sub cmbHide_Click()
  intLeft = Me.Left
  intTop = Me.Top
  hide
End Sub

Private Sub cmbInsert_Click()
   
   Dim objBlRef As AcadBlockReference
   Dim dM As Double
   Dim strCommand As String
   Dim intAttreq As Integer
   Dim intCmdEcho As Integer
   Dim oLayerKar As AcadLayer
   Dim oLayerActive As AcadLayer
   Dim bolLock As Boolean
   Dim bolFreeze As Boolean
   
'   If TextBoxBibl = "" Then
'      MsgBox "Нужно выбрать библиотеку"
'      Exit Sub
'   End If
   
   If TextBoxMarka = "" Then Exit Sub
   
'   TextBoxMarkaChange
   
   If objKar.strError <> "" Then
      MsgBox objKar.strError, vbCritical, psVBProjectName
      Exit Sub
   End If
   
   intLeft = Me.Left
   intTop = Me.Top
   
   Me.hide
   
'   If Not IsNumeric(TextBoxM) Then
'      MsgBox "Масштаб не определен!", vbCritical
'      Exit Sub
'   End If
   
'   dM = TextBoxM
   
   'для нормальной вставки блока каркаса на слой "каркасы"
   'слой каркасы нужно разморозить
   'слой каркасов может быть выключен, - нужно включить
   'но слой каркаса может быть закрыт - это пускай
   'запоминаем текущий слой, и делаем слой каркасов текущим
   Set oLayerActive = ThisDrawing.ActiveLayer
   Set oLayerKar = ThisDrawing.Layers.Item(Functions.GetLayer("Каркасы"))
   'включаем слой без разговоров
   oLayerKar.LayerOn = True
   'если слой каркасов не текущий, то он может быть замороженным
   If Not oLayerKar Is oLayerActive Then
      oLayerKar.Freeze = False
   End If
   'делаем текущим слой каркасов
   ThisDrawing.ActiveLayer = oLayerKar
   
   'процедура создания блока если его нет в коллекции
   CreateBlockKarkasa
   
   intAttreq = ThisDrawing.GetVariable("attreq")
   intCmdEcho = ThisDrawing.GetVariable("cmdecho")
   ThisDrawing.SetVariable "attreq", 0
   ThisDrawing.SetVariable "cmdecho", 0
   strCommand = "(command " & _
                   Chr(34) & "._-insert" & Chr(34) & " " & _
                   Chr(34) & objKar.strBlName & Chr(34) & " " & _
                   "pause 1 1 pause)(princ)"
'   strCommand = "(command " & _
'                   Chr(34) & "._-insert" & Chr(34) & _
'                   vbCr & Chr(34) & TextBoxMarka & _
'                   Chr(34) & " pause " & vbCr & _
'                   Chr(34) & "1" & Chr(34) & _
'                   vbCr & Chr(34) & "1" & _
'                   Chr(34) & " pause )"
                   
   ThisDrawing.SendCommand strCommand & vbCr
   ThisDrawing.SetVariable "attreq", intAttreq
   ThisDrawing.SetVariable "cmdecho", intCmdEcho
   'возвращаем старый текущий слой
   ThisDrawing.ActiveLayer = oLayerActive
   
   Me.Show
   
End Sub

Private Sub cmbName_Click()
   TextBoxPapka = ""
   TextBoxMarka = InputBox("Введите имя каркаса", "Новый каркас", TextBoxMarka)
End Sub

Private Sub cmbOptions_Click()
  FormOptions.Show
End Sub

Private Sub cmbRaschetMassy_Click()
  'заполняем параметры каркаса и обрабатываем каркас
  
  objKar.intLenSech = TextBoxLenSech
  'objKar.intHeightRost = TextBoxHeight
  objKar.intCenterVerhArm = TextBoxVerhZachBet
  objKar.intCenterNizArm = TextBoxNizZachBet
  If objKar.bolD = True Then
    objKar.intShagDopPopSter = TextBoxShagDopPopSter
  End If
  If objKar.bolP = True Then
    objKar.intDiamSvyzVerhArm = TextBoxDiamVerhSvyzSter
    objKar.intDiamSvyzNizArm = TextBoxDiamNizSvyzSter
    objKar.intShagSvyzVerhArm = TextBoxShagVerhSvyzSter
    objKar.intShagSvyzNizArm = TextBoxShagNizSvyzSter
  End If
  
  objKar.ObrabParam
  
  'заполняем поля результатов расчета
  
  TBMassaNaimVerh = objKar.sNaimVerhArm
  TBMassaKolVerh = 1
  TBMassaMassaEdVerh = FormatNumber(objKar.dMassaEdVerhSter, 2)
  TBMassaMassaVerh = FormatNumber(TBMassaMassaEdVerh, 2)
  TBMassaNaimNiz = objKar.sNaimNizArm
  TBMassaKolNiz = 1
  TBMassaMassaEdNiz = FormatNumber(objKar.dMassaEdNizSter, 2)
  TBMassaMassaNiz = FormatNumber(TBMassaMassaEdNiz, 2)
  TBMassaNaimPop = objKar.sNaimPopArm
  TBMassaKolPop = objKar.intKolPopSterPlosKar
  TBMassaMassaEdPop = FormatNumber(objKar.dMassaEdPopSter, 2)
  TBMassaMassaPop = FormatNumber(objKar.dMassaEdPopSter * objKar.intKolPopSterPlosKar, 2)
  'масса плоского каркаса
  TextBoxMassaPlosKar = FormatNumber(objKar.dMassaPlosKar, 2)
  'связевые стержни
  If objKar.bolP = True Then
    TBMassaNaimSvyzVerh = objKar.sNaimSvyzVerhArm
    TBMassaNaimSvyzNiz = objKar.sNaimSvyzNizArm
    TBMassaKolSvyzVerh = objKar.intKolSvyzVerhSter
    TBMassaKolSvyzNiz = objKar.intKolSvyzNizSter
    TBMassaMassaEdSvyzVerh = FormatNumber(objKar.dMassaEdSvyzVerhSter, 2)
    TBMassaMassaEdSvyzNiz = FormatNumber(objKar.dMassaEdSvyzNizSter, 2)
    TBMassaMassaSvyzVerh = FormatNumber(objKar.dMassaEdSvyzVerhSter * objKar.intKolSvyzVerhSter, 2)
    TBMassaMassaSvyzNiz = FormatNumber(objKar.dMassaEdSvyzNizSter * objKar.intKolSvyzNizSter, 2)
    'масса простр каркаса
    TextBoxMassaProsKar = FormatNumber(objKar.dMassaProsKar, 2)
  End If
  
End Sub

Private Sub ComboBoxFilterK_Change()
   'фильтр того что на листбоксе по типу плоского каркаса (К, КО, КД, Все)

   Dim i As Integer
   Dim strType As String
   Dim strName As String
   Dim strChr As String
   Dim typeNames() As FileBlock
   Dim intCount As Integer
   Dim intVal As Integer
   Dim strTypeInCombo As String

   strTypeInCombo = ComboBoxFilterK

   If strTypeInCombo = "" Then Exit Sub
   
   On Error GoTo HasError
   
   ComboBoxFilterP_Change
   If strTypeInCombo = "Все" Then
      Exit Sub
   End If
   
   For i = 0 To ListBoxBlocks.ListCount - 1
      'определяем тип К из имени блока
      strName = ListBoxBlocks.List(i, 0)
      intVal = InStr(LCase(strName), "к")
      strChr = Mid(LCase(strName), intVal + 1, 1)
      If strChr = "д" Then
         'значит это "КД"
         strType = "КД"
      ElseIf strChr = "о" Then
         'значит это "КО"
         strType = "КО"
      Else
         'значит это "К"
         strType = "К"
      End If
      'если совпадает с выбраным в фильтре то добавляем имя блока в массив
      If strType = strTypeInCombo Then
         ReDim Preserve typeNames(intCount)
         typeNames(intCount).FilesDwg = ListBoxBlocks.List(i, 0)
         typeNames(intCount).Path = ListBoxBlocks.List(i, 1)
         intCount = intCount + 1
      End If
   Next

   'очищаем листбокс, и заполняем его из массива
   ListBoxBlocks.Clear
   
   For i = 0 To UBound(typeNames)
      ListBoxBlocks.AddItem typeNames(i).FilesDwg
      ListBoxBlocks.List(i, 1) = typeNames(i).Path
   Next
   
Exit Sub
HasError:
End Sub

Private Sub ComboBoxFilterP_Change()
   'выводим список блоков по кол-ву "П"
   
   Dim objBlock As AcadBlock
   Dim i As Integer
   Dim j As Integer
   Dim intVal As Integer
   Dim strChr As String
   Dim strName As String
   Dim asTypeK(2) As String
   
   If ComboBoxFilterP = "" Then Exit Sub
   
   On Error GoTo HasError
   
   ListBoxBlocks.Clear
   
   Select Case ComboBoxFilterP
      Case "Все"
         For i = 0 To UBound(typeFiles)
            'добавляем имя блока в список
            ListBoxBlocks.AddItem typeFiles(i).FilesDwg, i
            ListBoxBlocks.List(i, 1) = typeFiles(i).Path
         Next
      Case "Плоские"
         j = 0
         For i = 0 To UBound(typeFiles)
            If InStr(typeFiles(i).FilesDwg, "П") = 0 Then
               'добавляем имя файла в список
               ListBoxBlocks.AddItem typeFiles(i).FilesDwg, j
               ListBoxBlocks.List(j, 1) = typeFiles(i).Path
               j = j + 1
            End If
         Next
      Case "Нестандартные"
         j = 0
         For i = 0 To UBound(typeFiles)
            If InStr(typeFiles(i).FilesDwg, "-") <> 0 Then
               'добавляем имя файла в список
               ListBoxBlocks.AddItem typeFiles(i).FilesDwg, j
               ListBoxBlocks.List(j, 1) = typeFiles(i).Path
               j = j + 1
            End If
         Next
      Case Else
         j = 0
         For i = 0 To UBound(typeFiles)
            'определяем кол плос каркасов (цифра перед "П")
            If InStr(typeFiles(i).FilesDwg, "П") <> 0 Then
               'значит это пространственный каркас
               If Val(typeFiles(i).FilesDwg) = CInt(Val(ComboBoxFilterP)) Then
                  'добавляем имя блока в список
                  ListBoxBlocks.AddItem typeFiles(i).FilesDwg, j
                  ListBoxBlocks.List(j, 1) = typeFiles(i).Path
                  j = j + 1
               End If
            End If
         Next
   End Select
   
   'заполняем этот комбобокс типами каркасов на листбокс
   AddTypeKToCombo

Exit Sub
HasError:
   
End Sub

Private Sub ComboBoxHvostLeft_Change()
  
  
End Sub

Private Sub ComboBoxHvostLeft_Exit(ByVal Cancel As MSForms.ReturnBoolean)
  'определение марки
  OprMarky
End Sub

Private Sub ComboBoxHvostRight_Change()
  
  
End Sub

Private Sub ComboBoxHvostRight_Exit(ByVal Cancel As MSForms.ReturnBoolean)
  'определение марки
  OprMarky
End Sub

Private Sub ListBoxBlocks_Click()
   
   Dim index As Integer
   
   index = ListBoxBlocks.ListIndex
   If index = -1 Then Exit Sub
   
   TextBoxMarka = ListBoxBlocks
   If bolKirp = False Then
    TextBoxPapka = ListBoxBlocks.List(index, 1)
   End If
   
   TextBoxMarkaChange
   
End Sub

'Private Sub TextBoxKolShtuk_Change()
'   'добавление (шт.Х) в текстбокс марки
'
'   If TextBoxKolShtuk = "" Then Exit Sub
'
'   If IsNumeric(CInt(TextBoxKolShtuk)) = False Then
'      MsgBox "Нужно ввести число!", vbCritical
'      Exit Sub
'   End If
'
'   If CInt(TextBoxKolShtuk) = 1 Or objKar.intKolShtuk = TextBoxKolShtuk Then
'      'делать ниче не надо
'      Exit Sub
'   End If
'
'   TextBoxMarka = objKar.strFirstName & "(шт." & TextBoxKolShtuk & ")"
'
'End Sub

Private Sub TextBoxMarkaChange()
   'выводим инфу по марке каркаса
   
   Set objKar = New clKarkas 'изм 25.10.2012
   
   If TextBoxMarka = "" Then Exit Sub
   
   'objKar.Name = TextBoxMarka
   If InStr(TextBoxMarka, "П") = 0 Then
      'все что после "-" - в нижний регистр, (шт.2) - отбрасываем
      objKar.ObrabName Functions.GetFirstNameKar(TextBoxMarka, False)
   Else
      'все что после "-" - в нижний регистр
      objKar.ObrabName Functions.GetFirstNameKar(TextBoxMarka, True)
   End If
   
   If objKar.strError <> "" Then
      MsgBox "Каркас - " & TextBoxMarka & vbCr & objKar.strError, vbCritical, psVBProjectName
      If ListBoxBlocks.ListIndex = -1 Then
        TextBoxMarka = sTBMarka
      Else
        TextBoxMarka = ListBoxBlocks
      End If
      Exit Sub
   End If
   
   objKar.intKolShtuk = TextBoxKolShtuk
   
   'определяем имя для блока каркаса
   If objKar.bolP = False Then
      If objKar.intKolShtuk > 1 Then
        objKar.strBlName = objKar.strFirstName & "(шт." & objKar.intKolShtuk & ")"
      Else
        objKar.strBlName = objKar.strFirstName
      End If
   Else
     objKar.strBlName = objKar.strFirstName
   End If
   
   TextBoxKolP = objKar.intP
   If objKar.intHvostLeft > objKar.intHvostRight Then
'      TextBoxHvostLeft = objKar.intHvostRight
'      TextBoxHvostRight = objKar.intHvostLeft
      ComboBoxHvostLeft = objKar.intHvostRight
      ComboBoxHvostRight = objKar.intHvostLeft
   Else
'      TextBoxHvostLeft = objKar.intHvostLeft
'      TextBoxHvostRight = objKar.intHvostRight
      ComboBoxHvostLeft = objKar.intHvostLeft
      ComboBoxHvostRight = objKar.intHvostRight
   End If
   TextBoxL = objKar.intLenRab
   TextBoxVerh = objKar.intDiamVerhArm
   TextBoxNiz = objKar.intDiamNizArm
   TextBoxPop = objKar.intDiamPopArm
   
   If objKar.bolHeightRostInName = False Then
     TextBoxMarka = objKar.strFirstName
   Else
     Dim sPrefHeight As String
     sPrefHeight = "(" & objKar.intHeightRost / 100 & ")"
     TextBoxMarka = objKar.strFirstName & sPrefHeight
     'objKar.strPlosKarName = objKar.strPlosKarName & sPrefHeight
   End If
   'высота ростверка
   TextBoxHeight = objKar.intHeightRost
   
   sTBMarka = TextBoxMarka
   
'   TextBoxMarka = objKar.strFirstName
    
    'определение маркиК
    If objKar.bolP = True Then
      TextBoxMarkaK = objKar.intP & "П" & objKar.strType
    Else
      TextBoxMarkaK = objKar.strType
    End If
    'определение номераК
    TextBoxNomerK = DefineNumK(objKar)
   
End Sub

Private Sub TextBoxHvostLeft_Exit(ByVal Cancel As MSForms.ReturnBoolean)
  'находим ближайшое значение стандартной длины хвоста
  TextBoxHvostLeft = GetNearStandartLenHvost(Val(TextBoxHvostLeft))
  'определение марки
  OprMarky
  
End Sub

Private Sub TextBoxHvostRight_Exit(ByVal Cancel As MSForms.ReturnBoolean)
  'находим ближайшое значение стандартной длины хвоста
  TextBoxHvostRight = GetNearStandartLenHvost(Val(TextBoxHvostRight))
  'определение марки
  OprMarky
End Sub

Private Sub TextBoxDiamNizSvyzSter_Exit(ByVal Cancel As MSForms.ReturnBoolean)
  If Functions.ProvDiamStandard(Val(TextBoxDiamNizSvyzSter)) = False Then
    MsgBox TextBoxDiamNizSvyzSter & " - этот диаметр не применим."
    TextBoxDiamNizSvyzSter = 8
  End If
End Sub

Private Sub TextBoxDiamVerhSvyzSter_Exit(ByVal Cancel As MSForms.ReturnBoolean)
  If Functions.ProvDiamStandard(Val(TextBoxDiamVerhSvyzSter)) = False Then
    MsgBox TextBoxDiamVerhSvyzSter & " - этот диаметр не применим."
    TextBoxDiamVerhSvyzSter = 8
  End If
End Sub

Private Sub TextBoxHeight_Exit(ByVal Cancel As MSForms.ReturnBoolean)
  TextBoxHeight = CInt(Val(TextBoxHeight))
  If CInt(TextBoxHeight) < 400 Then
    MsgBox "Минимальная высота ростверка 400", vbCritical, psVBProjectName
    TextBoxHeight = FormOptions.TextBoxHeightDef
  End If
  
  OprMarky
  
End Sub

Private Sub TextBoxHeightRost_Exit(ByVal Cancel As MSForms.ReturnBoolean)
  TextBoxHeightRost = CInt(Val(TextBoxHeightRost))
  If CInt(TextBoxHeightRost) < 200 Then
    MsgBox "Минимальная высота ростверка 200", vbCritical, psVBProjectName
    TextBoxHeightRost = 400
  End If
End Sub

Private Sub TextBoxKolP_Change()
  If TextBoxKolP = 1 Then
    TextBoxKolShtuk.Visible = True
    Label12.Visible = True
  Else
    TextBoxKolShtuk = 1
    TextBoxKolShtuk.Visible = False
    Label12.Visible = False
  End If
End Sub

Private Sub TextBoxKolP_Exit(ByVal Cancel As MSForms.ReturnBoolean)
  Dim intKolP As Integer
  intKolP = Val(TextBoxKolP)
  If intKolP <= 0 Then
    TextBoxKolP = 1
  Else
    TextBoxKolP = intKolP
  End If
  
  OprMarky
End Sub

Private Sub TextBoxKolShtuk_Exit(ByVal Cancel As MSForms.ReturnBoolean)
  Dim intKolShtuk As Integer
  intKolShtuk = Val(TextBoxKolShtuk)
  If intKolShtuk = 0 Then
    TextBoxKolShtuk = 1
    objKar.intKolShtuk = 1
  Else
    TextBoxKolShtuk = intKolShtuk
    objKar.intKolShtuk = intKolShtuk
  End If
  
  OprMarky
  
End Sub

Private Sub TextBoxL_Exit(ByVal Cancel As MSForms.ReturnBoolean)
  'определяем рабочую длину
  Dim intTBValue As Integer
  Dim intN As Integer
  Dim intLenRabRezult As Integer
  Dim iD As Integer
  Dim intLenRab1 As Integer
  Dim intLenRab2 As Integer
  Dim intLenRab3 As Integer
  Dim intDelta1 As Integer
  Dim intDelta2 As Integer
  Dim intDelta3 As Integer
  
  intTBValue = Val(TextBoxL)
  
  intN = intTBValue \ 150
  If bolKirp = True Then
    iD = (intTBValue - (intN * 150)) \ 10
    intLenRabRezult = (intN * 150) + (iD * 10)
  Else
    intLenRab1 = intN * 150
    intLenRab2 = (intN + 1) * 150
    intLenRab3 = intN * 150 + 100
    intDelta1 = Abs(intTBValue - intLenRab1)
    intDelta2 = Abs(intTBValue - intLenRab2)
    intDelta3 = Abs(intTBValue - intLenRab3)
    If intDelta1 < intDelta2 Then
      If intDelta1 < intDelta3 Then
        intLenRabRezult = intLenRab1
      Else
        intLenRabRezult = intLenRab3
      End If
    Else
      If intDelta2 < intDelta3 Then
        intLenRabRezult = intLenRab2
      Else
        intLenRabRezult = intLenRab3
      End If
    End If
  End If
  
  TextBoxL = intLenRabRezult
  
  OprMarky
  
End Sub

Private Sub TextBoxLenSech_Exit(ByVal Cancel As MSForms.ReturnBoolean)
  TextBoxLenSech = CInt(Val(TextBoxLenSech))
  If CInt(TextBoxLenSech) < 400 Then
    MsgBox "Минимальная ширина ростверка 400", vbCritical, psVBProjectName
    TextBoxLenSech = 500
  End If
End Sub

Private Sub TextBoxMarka_Exit(ByVal Cancel As MSForms.ReturnBoolean)
  If TextBoxMarka = "" Then Exit Sub
  TextBoxMarkaChange
  
  'если Д больше 150, то ставим галку
  If objKar.intShagDopPopSter > 150 Then
    CheckBoxD.Value = True
  Else
    CheckBoxD.Value = False
  End If
End Sub


Private Sub TextBoxMarkaK_Change()

End Sub

Private Sub TextBoxNiz_Exit(ByVal Cancel As MSForms.ReturnBoolean)
  If Functions.ProvDiamStandard(TextBoxNiz) = False Then
    MsgBox TextBoxNiz & " - этот диаметр не поддерживается.", vbCritical, psVBProjectName
    TextBoxNiz = iDiamNizDef
  End If
  
  OprMarky
  
End Sub

Private Sub TextBoxNizZachBet_Exit(ByVal Cancel As MSForms.ReturnBoolean)
  TextBoxNizZachBet = CInt(Val(TextBoxNizZachBet))
  If CInt(TextBoxNizZachBet) < 20 Then
    MsgBox "Минимальное расстояние от сентра нижней рабочей арматуры до низа ростверка 20"
    TextBoxNizZachBet = 80
  End If
End Sub

Private Sub TextBoxNomerK_Exit(ByVal Cancel As MSForms.ReturnBoolean)
  Dim iVal As Integer
  iVal = Val(TextBoxNomerK)
  If iVal < 1 Then
    MsgBox "Введите номер", vbExclamation, psVBProjectName
    TextBoxNomerK = 1
    Exit Sub
  End If
  TextBoxNomerK = iVal
  'для кирпички проверяем маркуК и номер в колекции
  ProvNumKinColKAndForm
  
  'TextBoxNomerK = iVal
End Sub

Private Sub TextBoxPop_Exit(ByVal Cancel As MSForms.ReturnBoolean)
  If Functions.ProvDiamStandard(TextBoxPop) = False Then
    MsgBox TextBoxPop & " - этот диаметр не поддерживается.", vbCritical, psVBProjectName
    TextBoxPop = iDiamPopDef
  End If
  
  OprMarky
  
End Sub

Private Sub TextBoxShagDopPopSter_Exit(ByVal Cancel As MSForms.ReturnBoolean)
  TextBoxShagDopPopSter = CInt(Val(TextBoxShagDopPopSter))
  If CInt(TextBoxShagDopPopSter) < 50 Then
    MsgBox "Минимальная шаг доп.поп.стержня 50", vbExclamation, psVBProjectName
    TextBoxShagDopPopSter = 100
  End If
End Sub

Private Sub TextBoxShagNizSvyzSter_Exit(ByVal Cancel As MSForms.ReturnBoolean)
  TextBoxShagNizSvyzSter = CInt(Val(TextBoxShagNizSvyzSter))
  If CInt(TextBoxShagNizSvyzSter) < 50 Then
    MsgBox "Минимальная шаг связевого стержня 50", vbExclamation, psVBProjectName
    TextBoxShagNizSvyzSter = 300
  End If
End Sub

Private Sub TextBoxShagVerhSvyzSter_Exit(ByVal Cancel As MSForms.ReturnBoolean)
  TextBoxShagVerhSvyzSter = CInt(Val(TextBoxShagVerhSvyzSter))
  If CInt(TextBoxShagVerhSvyzSter) < 50 Then
    MsgBox "Минимальная шаг связевого стержня 50", vbExclamation, psVBProjectName
    TextBoxShagVerhSvyzSter = 300
  End If
End Sub

Private Sub TextBoxVerh_Exit(ByVal Cancel As MSForms.ReturnBoolean)
  If Functions.ProvDiamStandard(TextBoxVerh) = False Then
    MsgBox TextBoxVerh & " - этот диаметр не поддерживается.", vbCritical, psVBProjectName
    TextBoxVerh = iDiamVerhDef
  End If
  
  OprMarky
  
End Sub
Private Sub TextBoxVerhZachBet_Exit(ByVal Cancel As MSForms.ReturnBoolean)
  TextBoxVerhZachBet = CInt(Val(TextBoxVerhZachBet))
  If CInt(TextBoxVerhZachBet) < 20 Then
    MsgBox "Минимальное расстояние от сентра верхней рабочей арматуры до верха ростверка 20", vbExclamation, psVBProjectName
    TextBoxVerhZachBet = 40
  End If
End Sub

Private Sub ToggleButtonMassa_Click()
   
   If ToggleButtonMassa.Value = True Then
      'Me.hide
      Me.Width = 504
      'Me.Show
   Else
      'Me.hide
      Me.Width = 240
      'Me.Show vbModeless
   End If
   
End Sub

Private Sub UserForm_Activate()
  
  If intLeft <> 0 Then
    Me.Left = intLeft
    Me.Top = intTop
  End If
  
  If bolKirp = True Then
    If pcolBadMarkaKBl.Count <> 0 Then
      Me.hide
    End If
  End If

End Sub

Private Function CreateBlockKarkasa()
   'создание блока каркаса на основе данных из objKar
      
   Dim objBlock As AcadBlock
   Dim oLine As AcadLine
   Dim oRabLine As AcadLine
   Dim oAttr As AcadAttribute
   Dim objBlRef As AcadBlockReference
   Dim oAttrRefMarka As AcadAttribute
   Dim oAtrShtuk As AcadAttribute
   Dim oLayerAttr As AcadLayer
   Dim oActivLayer As AcadLayer
   Dim objAtt As AcadAttribute
   Dim dPt(2) As Double
   Dim dPt2(2) As Double
   Dim dPtCentAttr(2) As Double
   Dim dPtAtrShtuk(2) As Double
   Dim sLayer As String
   Dim varArray As Variant
   Dim bolLock As Boolean
   Dim varExpl As Variant
   Dim strAttrFullPath As String
   Dim strBlFullPath As String
   
   On Error Resume Next
      Set objBlock = ThisDrawing.Blocks.Item(objKar.strBlName)
      'Сейчас не нужно сохр в библе 11/08/10
      If Err Then
         'ищем блок в библиотеке
'         strBlFullPath = GetPathToBiblBl(objKar.Name)
         If TextBoxPapka = "" Then
            'создаем новый блок
            Set objBlock = ThisDrawing.Blocks.add(dPt, objKar.strBlName)
         Else
            'определяем путь к файлу блока в библиотеке
            strBlFullPath = msBiblPath & "\" & TextBoxPapka & "\" & TextBoxMarka & ".dwg"
            If Dir(strBlFullPath) = "" Then
               'создаем новый блок
               Set objBlock = ThisDrawing.Blocks.add(dPt, objKar.strBlName)
            Else
               'вставляем блок
               Set objBlRef = ThisDrawing.ModelSpace.InsertBlock(dPt, strBlFullPath, 1, 1, 1, 0)
               objBlRef.Delete
               Exit Function
            End If
         End If
      Else
         'если есть такой блок, то выходим
         If bolKirp = True Then
            'проверяем маркуК и проверяем атрибут марки (9)-высоту ростверка
            AddAtrMarkaKToBlock objBlock
            Set objBlock = ThisDrawing.Blocks.Item(objKar.strBlName)
         End If
         Exit Function
      End If
   On Error GoTo 0
   
   'текущий слой нужно разблокировать
   Set oActivLayer = ThisDrawing.ActiveLayer
   If oActivLayer.Lock = True Then
      bolLock = True
      oActivLayer.Lock = False
   End If
   
   dPt2(0) = objKar.intLenRab
   'первая линия (в рабочей длине)
   Set oRabLine = objBlock.AddLine(dPt, dPt2)
   oRabLine.Layer = "Каркасы"
   oRabLine.color = acByLayer
   
   'вертикальные линии (границы рабочей зоны каркаса и хвостов)
   'вторая вертик линия
   dPt(0) = oRabLine.EndPoint(0): dPt(1) = -75
   dPt2(0) = oRabLine.EndPoint(0): dPt2(1) = 75
   Set oLine = objBlock.AddLine(dPt, dPt2)
   oLine.Layer = "Каркасы"
   'правый хвост
   dPt(1) = 0
   dPt2(0) = dPt(0) + objKar.intHvostRight: dPt2(1) = 0
   Set oLine = objBlock.AddLine(dPt, dPt2)
   oLine.Layer = "Каркасы"
   oLine.color = acByLayer
   
   If objKar.bolD = True Then
      'рисуем вертик линию доп.попер.стержня
      dPt(0) = oRabLine.EndPoint(0) - objKar.intShagDopPopSter: dPt(1) = -75
      dPt2(0) = oRabLine.EndPoint(0) - objKar.intShagDopPopSter: dPt2(1) = 75
      Set oLine = objBlock.AddLine(dPt, dPt2)
      oLine.Layer = "Каркасы"
      oLine.color = acByLayer
   End If
   
   'первая вертик линия
   dPt(0) = 0: dPt(1) = -75
   dPt2(0) = 0: dPt2(1) = 75
   Set oLine = objBlock.AddLine(dPt, dPt2)
   oLine.Layer = "Каркасы"
   'левый хвост
   dPt(0) = 0: dPt(1) = 0
   dPt2(0) = dPt(0) - objKar.intHvostLeft: dPt2(1) = 0
   Set oLine = objBlock.AddLine(dPt, dPt2)
   oLine.Layer = "Каркасы"
   oLine.color = acByLayer
   
   'точка середины каркаса
   dPtCentAttr(0) = oRabLine.EndPoint(0) / 2
   dPtCentAttr(1) = 60
   
   'вставляем блок атрибута из \\Sgpsrv2\СПД\Конструкторы\Макросы\SpecRost\Attr.dwg
   strAttrFullPath = Functions.GetMacroFolder(psVBProjectName) & "\Блоки\Attr.dwg"
   Set objBlRef = objBlock.InsertBlock(dPt, strAttrFullPath, 1, 1, 1, 0)
   varExpl = objBlRef.Explode
   objBlRef.Delete
   'востанавливаем блокировку слоя
   If bolLock = True Then
      oActivLayer.Lock = True
   End If
   
   Set oAttrRefMarka = varExpl(0)
   'прежде чем передвигать атрибут в точку центра каркаса,
   'нужно проверить блокировку слоя
   Set oLayerAttr = ThisDrawing.Layers(oAttrRefMarka.Layer)
   If oLayerAttr.Lock = True Then
      bolLock = True
      oLayerAttr.Lock = False
   End If
   oAttrRefMarka.TextAlignmentPoint = dPtCentAttr
   oAttrRefMarka.TagString = objKar.strBlName ' objKar.strFirstName
   oAttrRefMarka.TextString = TextBoxMarka  'objKar.strFirstName
   'маркаК
   If bolKirp = True Then
      'добавляем атрибут КР
      Set objAtt = oAttrRefMarka.Copy
'      If objKar.bolП = True Then
'        objAtt.TextString = Val(objKar.strFirstName) & "ПК1"
'      Else
'        objAtt.TextString = "К1"
'      End If
      objAtt.TextString = TextBoxMarkaK & TextBoxNomerK
      objAtt.PromptString = "МаркаК"
      objAtt.TagString = "МаркаК"
      objAtt.Layer = "Каркасы"
      objAtt.Lineweight = acLnWt025
      'передвигаем атрибут настоящей марки
      dPtCentAttr(1) = dPtCentAttr(1) - 375
      oAttrRefMarka.TextAlignmentPoint = dPtCentAttr
   End If
   
   'если (шт.2), вставляем еще один атрибут
   If objKar.intKolShtuk > 1 Then
      If bolKirp = True Then
        'передвигаем атрибут марки
        dPtCentAttr(1) = dPtCentAttr(1) - 300
        oAttrRefMarka.TextAlignmentPoint = dPtCentAttr
        dPtAtrShtuk(0) = dPtCentAttr(0): dPtAtrShtuk(1) = dPtCentAttr(1) + 300
      Else
        dPtCentAttr(1) = dPtCentAttr(1) - 375
        dPtAtrShtuk(0) = dPtCentAttr(0): dPtAtrShtuk(1) = dPtCentAttr(1)
      End If
      Set oAtrShtuk = oAttrRefMarka.Copy
'      oAttrRefMarka.TextString = objKar.strFirstName
      oAtrShtuk.Lineweight = acLnWt025
      oAtrShtuk.PromptString = "кол."
      oAtrShtuk.TextString = "шт." & objKar.intKolShtuk
      oAtrShtuk.TextAlignmentPoint = dPtAtrShtuk
      oAtrShtuk.Layer = "Каркасы"
   End If
   'вставляем атрибут массы и конструкции
   'создаем атрибут массы
         Set objAtt = oAttrRefMarka.Copy
         objAtt.Layer = Functions.GetLayer("Att~Massa")
         dPtCentAttr(1) = dPtCentAttr(1) - 300
         objAtt.TextAlignmentPoint = dPtCentAttr
         objAtt.Invisible = True
         objAtt.PromptString = "МАССА"
         objAtt.TextString = ""
         'создаем атрибут конструкции
         Set objAtt = oAttrRefMarka.Copy
         objAtt.Layer = Functions.GetLayer("Att~Constr")
         dPtCentAttr(1) = dPtCentAttr(1) - 300
         objAtt.TextAlignmentPoint = dPtCentAttr
         objAtt.Invisible = True
         objAtt.PromptString = "Конструкция"
         objAtt.TextString = "Ростверк"
   
   If bolLock = True Then oLayerAttr.Lock = True
   
   Dim strFolder As String
   Dim selSet As AcadSelectionSet
   Dim oEnt() As AcadEntity
   Dim bolY As Boolean
   
  If bolKirp = False Then
   'сохраняем блок в библиотеке
   If msBiblPath <> "" Then
     Set objBlRef = ThisDrawing.ModelSpace.InsertBlock(dPt, objKar.strBlName, 1, 1, 1, 0)
     'ищем папку для сохранения блока
     strFolder = Dir(msBiblPath & "\", vbDirectory)
     Do Until strFolder = ""
        If InStr(objKar.strBlName, "-") = 0 Then
           If objKar.bolP = True Then
              If InStr(strFolder, objKar.strType) <> 0 Then
               If objKar.strType = "К" Then
                 If InStr(strFolder, "КД") <> 0 Or InStr(strFolder, "КО") <> 0 Then
                    GoTo NextFolder
                 End If
               End If
                 If InStr(strFolder, Val(objKar.strBlName) & "П") <> 0 Then
                    bolY = True
                    Exit Do
                 End If
              End If
           Else
              If LCase(strFolder) = "плоские каркасы" Then
                 bolY = True
                 Exit Do
              End If
           End If
        Else
           'папка нестандартных каркасов
           If InStr(strFolder, "Нестандартные") <> 0 Then
              If strFolder = "Нестандартные " & objKar.strType Then
                 bolY = True
                 Exit Do
              End If
           End If
        End If
    
NextFolder:
        strFolder = Dir()
     Loop
     
     Dim vExploded As Variant
     
     vExploded = objBlRef.Explode
  '   Set oEnt() = vExploded
     
     Set selSet = Functions.GetSelSet("Блок")
     selSet.AddItems vExploded
     
     If bolY = False Then
        'имя папки
        If InStr(objKar.strBlName, "-") = 0 Then
           If objKar.bolP = True Then
              strFolder = Val(objKar.strBlName) & "П " & objKar.strType
           Else
              strFolder = "Плоские каркасы"
           End If
        Else
           'папка нестандартных каркасов
           strFolder = "Нестандартные " & objKar.strType
        End If
        'создаем папку
        MkDir (msBiblPath & "\" & strFolder)
     End If
     ThisDrawing.Wblock msBiblPath & "\" & strFolder & "\" & objKar.strBlName & ".dwg", selSet
     
     objBlRef.Delete
     selSet.Erase
   End If
End If 'CheckBoxKR.Value = False
   
   'добавляем блок в листбокс
   ListBoxBlocks.AddItem TextBoxMarka, 0
   If bolKirp = False Then
    ListBoxBlocks.List(0, 1) = strFolder
   Else
    ListBoxBlocks.List(0, 1) = TextBoxMarkaK & TextBoxNomerK
   End If
   
   'добавление номераК в коллекцию
   Functions.AddNumKAndPlosKar TextBoxNomerK, objKar.strPlosKarName, objKar.strType
   
End Function

Private Sub AddKolPToCombo()
   'заполняем массив для фильтра по кол-ву Плоских кар, Плоские кар, Все
   
   Dim i As Integer
   Dim j As Integer
   Dim intCounter As Integer
   Dim intP As Integer
   Dim bolYes As Boolean
   Dim objBlock As AcadBlock
   
   ReDim aintTypeKar(0)
   For intCounter = 0 To ListBoxBlocks.ListCount - 1
      'определяем кол плос каркасов (цифра перед "П")
      If InStr(LCase(ListBoxBlocks.List(intCounter, 0)), "п") <> 0 Then
         'значит это пространственный каркас
         intP = Val(ListBoxBlocks.List(intCounter, 0))
      End If
      'проверяем массив, есть ли уже такое кол П
      bolYes = False
      For i = 0 To UBound(aintTypeKar)
         If aintTypeKar(i) = intP Then bolYes = True
      Next
      If bolYes = False Then
         'добавляем "П" в массив
         i = UBound(aintTypeKar) + 1
         ReDim Preserve aintTypeKar(i)
         aintTypeKar(i) = intP
      End If
   Next
   'сортируем asTypeKar
   For i = 1 To UBound(aintTypeKar)
      For j = 0 To UBound(aintTypeKar) - i
         If aintTypeKar(j) > aintTypeKar(j + 1) Then
            intP = aintTypeKar(j)
            aintTypeKar(j) = aintTypeKar(j + 1)
            aintTypeKar(j + 1) = intP
         End If
      Next
   Next
   'заполняем комбобокс фильтра
   ComboBoxFilterP.Clear
   ComboBoxFilterP.AddItem "Все"
   ComboBoxFilterP.AddItem "Плоские"
   ComboBoxFilterP.AddItem "Нестандартные"
   For i = 1 To UBound(aintTypeKar)
      ComboBoxFilterP.AddItem aintTypeKar(i) & "П"
   Next
   
'   'заполняем комбобокс тиов К в текущем списке листбокса
'   AddTypeKToCombo
   
End Sub

Private Sub SetBlocksFromBiblToArray()
   'вывод списка блоков из библиотеки в листбокс
   
   Dim strFileName As String
   Dim strFolderName As String
   Dim i As Integer
   Dim j As Integer
   Dim typePath() As Path
   
   Dim intFilesCount As Integer
   
   Erase typePath
   
   On Error GoTo HasError
   
   'файлом блока каркаса - в имени которого есть "К", и нет "сх"
   
   'смотрим только во вложенных папках,
   '(в корневом каталоге только схемы)
   'записываем массив вложенных папок
   strFolderName = Dir(msBiblPath & "\", vbDirectory)
   Do Until strFolderName = ""
    If InStr(strFolderName, ".") = 0 Then
      If InStr(strFolderName, "П") <> 0 And InStr(strFolderName, "К") Or LCase(strFolderName) = "плоские каркасы" Or strFolderName Like ("Нестандартные*") Then
         ReDim Preserve typePath(i)
         typePath(i).Path = strFolderName
         i = i + 1
      End If
    End If
      strFolderName = Dir()
   Loop
   
   If i = 0 Then
      Exit Sub
   End If
   
   'заносим имена файлов блоков каркасов
   For i = 0 To UBound(typePath)
      strFileName = Dir(msBiblPath & "\" & typePath(i).Path & "\*.dwg")
      If strFileName = "" Then
'         'удаляем папку
'         RmDir msBiblPath & "\" & typePath(i).Path
      End If
      Do Until strFileName = ""
         If InStr(strFileName, "К") <> 0 And InStr(LCase(strFileName), "сх") = 0 Then
            ReDim Preserve typePath(i).FilesDwg(j)
            typePath(i).FilesDwg(j) = Functions.GetNameWithoutExt(strFileName)
            j = j + 1
         End If
         strFileName = Dir
      Loop
      If j <> 0 Then
         typePath(i).IsFiles = True
         'суммарное кол-во файлов
         intFilesCount = intFilesCount + j
      End If
      j = 0 'сбрасываем счетчик
   Next
   'заполняем массив файлов typeFiles
   ReDim typeFiles(intFilesCount - 1)
   intFilesCount = 0
   For i = 0 To UBound(typePath)
      If typePath(i).IsFiles = True Then
         For j = 0 To UBound(typePath(i).FilesDwg)
            typeFiles(intFilesCount).Path = typePath(i).Path
            typeFiles(intFilesCount).FilesDwg = typePath(i).FilesDwg(j)
            intFilesCount = intFilesCount + 1
         Next
      End If
   Next
   
   SortyrTypeFiles typeFiles
   
   'заполняем листбокс
   ListBoxBlocks.Clear
   For i = 0 To UBound(typeFiles)
      ListBoxBlocks.AddItem typeFiles(i).FilesDwg, i
      ListBoxBlocks.List(i, 1) = typeFiles(i).Path
   Next

Exit Sub
HasError:
   MsgBox Err.Description, vbCritical, psVBProjectName
End Sub

Private Sub SortyrTypeFiles(ByRef typeFiles() As FileBlock)
   'сортировка имен блоков
   Dim i As Integer
   Dim j As Integer
   Dim typeFileTemp As FileBlock
      
   For i = 1 To UBound(typeFiles)
      For j = 0 To UBound(typeFiles) - i
         If StrComp(typeFiles(j).FilesDwg, typeFiles(j + 1).FilesDwg, vbTextCompare) = 1 Then
            typeFileTemp = typeFiles(j)
            typeFiles(j) = typeFiles(j + 1)
            typeFiles(j + 1) = typeFileTemp
         End If
      Next
   Next
   
End Sub

Private Sub UserForm_Click()
  Me.cmbInsert.SetFocus
End Sub

Private Sub UserForm_Initialize()
   'связь объекта ини файлом
   Dim strMacroFolder As String
   Dim sValue As String
   
   strMacroFolder = Functions.GetMacroFolder(psVBProjectName) & "\Ini"
   FileIni.CreateIni msFileIniName, strMacroFolder
   
   Dim objBlock As AcadBlock
   Dim i As Integer
    
  On Error Resume Next
   'On Error GoTo HasError
   
   'стандартные диаметры
   iDiamVerhDef = FileIni.GetFile("Настройки", "Диаметр верхней арм")
   If iDiamVerhDef = 0 Then iDiamVerhDef = 12
   FormOptions.TextBoxVerh = iDiamVerhDef
   iDiamNizDef = FileIni.GetFile("Настройки", "Диаметр нижней арм")
   If iDiamNizDef = 0 Then iDiamNizDef = 10
   FormOptions.TextBoxNiz = iDiamNizDef
   iDiamPopDef = FileIni.GetFile("Настройки", "Диаметр поперечной арм")
   If iDiamPopDef = 0 Then iDiamPopDef = 8
   FormOptions.TextBoxPop = iDiamPopDef
   FormOptions.TextBoxHeightDef = FileIni.GetFile("Настройки", "Высота ростверка")
   If Val(FormOptions.TextBoxHeightDef) = 0 Then FormOptions.TextBoxHeightDef = 500
   'Хвосты
    sValue = FileIni.GetFile("Настройка", "Хвосты")
    GetFieldHvostsFromString sValue, False
    sValue = FileIni.GetFile("Настройка", "Хвосты-кирпичка")
    GetFieldHvostsFromString sValue, True
  
  On Error GoTo 0
  
  'если кирпичка
  If bolKirp = False Then
    'скрываем Д,мм
    TextBoxD.Visible = False
    CheckBoxD.Visible = False
    Label147.Visible = False
    
    Label1K.Visible = False
    TextBoxMarkaK.Visible = False
    TextBoxNomerK.Visible = False
    
    Label8.Visible = True
    Label9.Visible = True
    ComboBoxFilterP.Visible = True
    ComboBoxFilterK.Visible = True
    Label10.Visible = True
    TextBoxPapka.Visible = True
    
    cmbBibl.Visible = True
    cmbExplorer.Visible = True
    TextBoxBibl.Visible = True
    
    'заполняем комбобоксы хвостов
    ComboBoxHvostLeft.AddItem FormOptions.TextBoxHvost0, 0
    ComboBoxHvostLeft.AddItem FormOptions.TextBoxHvost1, 1
    ComboBoxHvostLeft.AddItem FormOptions.TextBoxHvost2, 2
    ComboBoxHvostLeft.AddItem FormOptions.TextBoxHvost3, 3
    ComboBoxHvostLeft.AddItem FormOptions.TextBoxHvost4, 4
    ComboBoxHvostLeft.AddItem FormOptions.TextBoxHvost5, 5
    ComboBoxHvostLeft.AddItem FormOptions.TextBoxHvost6, 6
    ComboBoxHvostLeft.AddItem FormOptions.TextBoxHvost7, 7
    ComboBoxHvostLeft.AddItem FormOptions.TextBoxHvost8, 8
    ComboBoxHvostLeft.AddItem FormOptions.TextBoxHvost9, 9
    ComboBoxHvostLeft.AddItem FormOptions.TextBoxHvostik, 10
    ComboBoxHvostRight.List = ComboBoxHvostLeft.List
    
     'считываем библиотеку с ини
     msBiblPath = Functions.GetCorrectPath(FileIni.GetFile(msSection, msKeyBiblPath))
On Error Resume Next
     If Dir(msBiblPath, vbDirectory) = "" Then
On Error GoTo 0
  '      MsgBox "Выберете библиотеку!", vbExclamation
  '      cmbBibl_Click
        Dim msg As String
        msg = "Путь к библиотеке не найден. - " + msBiblPath
        MsgBox msg, vbInformation, psVBProjectName
        msBiblPath = ""
        Exit Sub
     End If
     TextBoxBibl = msBiblPath
     SetBlocksFromBiblToArray
     'заполнение комбобокса фильтра по кол П, и комбобокс фильтра по типуК
     AddKolPToCombo
  Else
    'для кирпички:
    ListBoxBlocks.ColumnCount = 2
    ListBoxBlocks.ColumnWidths = "85,40"
    TextBoxPapka = ""
    Label1K.Visible = True
    TextBoxMarkaK.Visible = True
    TextBoxNomerK.Visible = True
    
    Label8.Visible = False
    Label9.Visible = False
    ComboBoxFilterP.Visible = False
    ComboBoxFilterK.Visible = False
    Label10.Visible = False
    TextBoxPapka.Visible = False
    
    cmbBibl.Visible = False
    cmbExplorer.Visible = False
    TextBoxBibl.Visible = False
    
    'заполняем комбобоксы хвостов
    ComboBoxHvostLeft.AddItem FormOptions.TextBoxHvostK0, 0
    ComboBoxHvostLeft.AddItem FormOptions.TextBoxHvostK1, 1
    ComboBoxHvostLeft.AddItem FormOptions.TextBoxHvostK2, 2
    ComboBoxHvostLeft.AddItem FormOptions.TextBoxHvostK3, 3
    ComboBoxHvostLeft.AddItem FormOptions.TextBoxHvostK4, 4
    ComboBoxHvostLeft.AddItem FormOptions.TextBoxHvostK5, 5
    ComboBoxHvostLeft.AddItem FormOptions.TextBoxHvostK6, 6
    ComboBoxHvostLeft.AddItem FormOptions.TextBoxHvostK7, 7
    ComboBoxHvostLeft.AddItem FormOptions.TextBoxHvostK8, 8
    ComboBoxHvostLeft.AddItem FormOptions.TextBoxHvostK9, 9
    ComboBoxHvostLeft.AddItem FormOptions.TextBoxHvostikK, 10
    ComboBoxHvostRight.List = ComboBoxHvostLeft.List
    
    ComboBoxHvostLeft = FormOptions.TextBoxHvostikK
    ComboBoxHvostRight = FormOptions.TextBoxHvostikK
    
    'сканирование блоков каркасов на чертеже и создание коллекций номеровК
    ScanDrawToBlKarAndMarkaK
    
'    'выводим список каркасов в этом чертеже
'    SetBlockToListFromDrawing
    
  End If
   
Exit Sub
HasError:
   Select Case Err.Number
      Case 9
         'out of range
      Case Else
         MsgBox Err.Description, vbCritical, psVBProjectName
   End Select

End Sub

Private Sub AddTypeKToCombo()
   'заполнение комбобокса типов К, из списка листбокса
   Dim i As Integer
   Dim intVal As Integer
   Dim strChr As String
   Dim strName As String
   Dim asTypeK(2) As String
   
   On Error GoTo HasError
   
   'определяем массив типов плоских каркасов
   For i = 0 To ListBoxBlocks.ListCount - 1
      'определяем тип К из имени блока
      strName = LCase(ListBoxBlocks.List(i, 0))
      intVal = InStr(strName, "к")
      strChr = Mid(strName, intVal + 1, 1)
      If strChr = "д" Then
         'значит это "КД"
         If asTypeK(0) = "" Then
            asTypeK(0) = "КД"
         End If
      ElseIf strChr = "о" Then
         'значит это "КО"
         If asTypeK(1) = "" Then
            asTypeK(1) = "КО"
         End If
      Else
         'значит это "К"
         If asTypeK(2) = "" Then
            asTypeK(2) = "К"
         End If
      End If
   Next
   
   ComboBoxFilterK.Clear
   For i = 0 To 2
      If asTypeK(i) <> "" Then
         ComboBoxFilterK.AddItem asTypeK(i)
      End If
   Next
   ComboBoxFilterK.AddItem "Все"
   
'   Dim objBlock As AcadBlock
'
'   'считываем библиотеку с ини
'   msBiblPath = FileIni.GetFile(msSection, msKeyBiblPath)
'   If msBiblPath = "" Then
'      MsgBox "Выберете библиотеку!", vbExclamation
'      cmbBibl_Click
'      Exit Sub
'   End If
'
'   SetBlocksFromBiblToArray
'
'   'заполняем листбокс
'   ListBoxBlocks.Clear
'   For i = 0 To UBound(typeFiles)
'      ListBoxBlocks.AddItem typeFiles(i).FilesDwg, i
'      ListBoxBlocks.List(i, 1) = typeFiles(i).Path
'   Next
'
'   'заполнение комбобокса фильтра по кол П, и комбобокс фильтра по типуК
'   AddKolPToCombo
'
'   TextBoxBibl = msBiblPath
   
Exit Sub
HasError:
   Select Case Err.Number
      Case 9
         'out of range
      Case Else
         MsgBox Err.Description, vbCritical, psVBProjectName
   End Select
   
End Sub

Private Function GetPathToBiblBl(BlName As String) As String
   'поиск блока в библиотеке
   
   Dim intValue As Integer
   Dim intП As Integer
   Dim strFolder As String
   Dim strFullPathToBl As String
   Dim strVal As String
   
   If InStr(BlName, "-") = 0 Then
      'определяем кол-во П
      intValue = InStr(LCase(BlName), "п")
      If intValue = 0 Then
         'находим папку с плоскими каркасами соотв-щего типа каркасов
         strFolder = GetFolderPlosKar()
         If strFolder <> "" Then
            'ищем файл в этой папке
            strFullPathToBl = strFolder & "\" & BlName & ".dwg"
         End If
      Else
         intП = Val(BlName)
         'находим папку с таким кол-вом П и типом каркаса (навзвание папки м/б таким: "5П,6П,7П,10П КД")
         strFolder = GetFolderWithП(intП)
         If strFolder <> "" Then
            'ищем файл блока по диру
            strFullPathToBl = strFolder & "\" & BlName & ".dwg"
         End If
      End If
   Else
      'папка нестандартных каркасов
      If objKar.strType = "КД" Then
         strFullPathToBl = msBiblPath & "\Нестандартные КД\" & BlName & ".dwg"
      ElseIf objKar.strType = "КО" Then
         strFullPathToBl = msBiblPath & "\Нестандартные КО\" & BlName & ".dwg"
      ElseIf objKar.strType = "К" Then
         strFullPathToBl = msBiblPath & "\Нестандартные К\" & BlName & ".dwg"
      Else
         MsgBox "Ошибка определения типа каркаса!", vbCritical, psVBProjectName
         Exit Function
      End If
   End If
   
   strVal = Dir(strFullPathToBl)
   If strVal = "" Then strFullPathToBl = ""
   
   'если найден файл то возвращаем полный путь
   GetPathToBiblBl = strFullPathToBl
   
End Function

Private Function GetFolderWithП(intП As Integer) As String
   'поиск папки в библиотеке с таким кол-вом П (5П,7П, и т.д.)
   'возвращает полный путь к папке
   
   Dim strFolderName As String
   Dim intVal As Integer
   Dim i As Integer
   Dim bolY As Boolean
   
   strFolderName = Dir(msBiblPath & "\", vbDirectory)
   Do Until strFolderName = ""
      intVal = InStr(strFolderName, objKar.strType)
      If intVal <> 0 Then
       If objKar.strType = "К" Then
         If InStr(strFolderName, "КД") <> 0 And InStr(strFolderName, "КО") <> 0 Then
            GoTo NextFolder
         End If
       End If
       intVal = InStr(strFolderName, intП & "П")
         If intVal <> 0 Then
            bolY = True
            Exit Do
         End If
      End If
NextFolder:
      strFolderName = Dir()
   Loop
   
   If bolY = True Then
      GetFolderWithП = msBiblPath & "\" & strFolderName
   Else
      GetFolderWithП = ""
   End If
   
End Function

Private Function GetFolderPlosKar() As String
   'поиск папки плоских каркасов в библиотеке
   'возвращает полный путь к папке
   
   Dim strFolderName As String
   Dim bolY As Boolean
   
   strFolderName = Dir(msBiblPath & "\", vbDirectory)
   Do Until strFolderName = ""
      If LCase(strFolderName) = "плоские каркасы" Then
         bolY = True
         Exit Do
      End If
      strFolderName = Dir()
   Loop
   
   If bolY = True Then
      GetFolderPlosKar = msBiblPath & "\" & strFolderName
   Else
      GetFolderPlosKar = ""
   End If
   
End Function

Private Sub OprMarky()
  'определение марки каркаса по значениям полей параметров каркаса
  'по значениям полей можно опеделить марку плоского карокаса
  
  Dim sMarka As String
  Dim intN As Integer
  Dim intD As Integer
  Dim strType As String
  Dim iNumHvostLeft As Integer
  Dim iNumHvostRight As Integer
  Dim intHvostik As Integer
  Dim bolNestandart As Boolean
  Dim bolD As Boolean
  
'  'проверяем все ли поля заполнены
'  if TextBoxL ="" or TextBoxHvostLeft  ="" or TextBoxHvostRight  ="" _
'    TextBoxVerh = "" Or TextBoxNiz = "" Or TextBoxPop = ""
  
  'кол П
  If CInt(Val(TextBoxKolP)) > 1 Then
    sMarka = CInt(Val(TextBoxKolP)) & "П"
  End If
  'n*150
  intN = Val(TextBoxL) \ 150
  If TextBoxL Mod 150 > 0 Then
    bolD = True
    If bolKirp = True Then
      intD = (Val(TextBoxL) - (intN * 150)) \ 10
      'второй вариант д
      TextBoxD = intD * 10 + 150
    End If
  End If
  
  'если нажата галка для второго аварианта Д
  If bolKirp = True And CheckBoxD.Value = True Then
    'уменьшаем intN на 1, к Д прибавляем 150
    intN = intN - 1
    intD = intD + 15
  End If
  
  'добавляем к марке кол N
  sMarka = sMarka & intN
  
  'определяем тип каркаса
  If bolKirp = False Then
    intHvostik = FormOptions.TextBoxHvostik
  Else
    intHvostik = FormOptions.TextBoxHvostikK
  End If
  If ComboBoxHvostLeft.Value = intHvostik And ComboBoxHvostRight.Value = intHvostik Then
    strType = "К"
    sMarka = sMarka & strType
  ElseIf ComboBoxHvostLeft.Value = intHvostik Or ComboBoxHvostRight.Value = intHvostik Then
    strType = "КО"
    sMarka = sMarka & strType
    If ComboBoxHvostLeft.Value = intHvostik Then
'      iNumHvostRight = Functions.GetNumHvosta(TextBoxHvostRight)
      iNumHvostRight = ComboBoxHvostRight.ListIndex
    Else
'      iNumHvostRight = Functions.GetNumHvosta(TextBoxHvostLeft)
       iNumHvostRight = ComboBoxHvostLeft.ListIndex
    End If
    If iNumHvostRight <> 0 Then
      sMarka = sMarka & iNumHvostRight
    End If
  Else
    'КД
    strType = "КД"
    sMarka = sMarka & strType
'    iNumHvostLeft = Functions.GetNumHvosta(TextBoxHvostLeft)
      iNumHvostLeft = ComboBoxHvostLeft.ListIndex
'    iNumHvostRight = Functions.GetNumHvosta(TextBoxHvostRight)
      iNumHvostRight = ComboBoxHvostRight.ListIndex
    If iNumHvostRight = 0 And iNumHvostLeft = 0 Then
    ElseIf iNumHvostLeft = 0 Then
      sMarka = sMarka & iNumHvostRight & "0"
    ElseIf iNumHvostRight = 0 Then
      sMarka = sMarka & iNumHvostLeft & "0"
    Else
      If ReturnLenHvosta(iNumHvostLeft) < ReturnLenHvosta(iNumHvostRight) Then
        sMarka = sMarka & iNumHvostLeft & iNumHvostRight
      Else
        sMarka = sMarka & iNumHvostRight & iNumHvostLeft
      End If
    End If
  End If
  'диаметры
  If TextBoxVerh <> iDiamVerhDef And TextBoxNiz <> iDiamNizDef _
    And TextBoxVerh = TextBoxNiz Then
    'вн
    sMarka = sMarka & "-вн" & TextBoxVerh
    bolNestandart = True
  Else
    If TextBoxVerh <> iDiamVerhDef Then
      'в
      sMarka = sMarka & "-в" & TextBoxVerh
      bolNestandart = True
    End If
    If TextBoxNiz <> iDiamNizDef Then
      'н
      If bolNestandart = False Then
        bolNestandart = True
        sMarka = sMarka & "-н" & TextBoxNiz
      Else
        sMarka = sMarka & "н" & TextBoxNiz
      End If
    End If
  End If
  If TextBoxPop <> iDiamPopDef Then
    'п
    If bolNestandart = False Then
      bolNestandart = True
      sMarka = sMarka & "-п" & TextBoxPop
    Else
      sMarka = sMarka & "п" & TextBoxPop
    End If
  End If
  'Д
  If bolD = True Then
    If bolNestandart = False Then
      bolNestandart = True
      sMarka = sMarka & "-д"
    Else
      sMarka = sMarka & "д"
    End If
    If bolKirp = True Then
      If intD <> 10 Then 'десятку мы не показываем , она по умолчанию (100)
        sMarka = sMarka & intD
      End If
    End If
  End If
'  If TextBoxKolShtuk <> 1 Then
'    sMarka = sMarka & "(шт." & TextBoxKolShtuk & ")"
'  End If
  
  'высота ростверка (6)
  If TextBoxHeight <> FormOptions.TextBoxHeightDef Then
    TextBoxMarka = sMarka & "(" & Val(TextBoxHeight) \ 100 & ")"
  Else
    TextBoxMarka = sMarka
  End If
  TextBoxMarkaChange
  
End Sub

Private Function GetNearStandartLenHvost(intLen As Integer) As Integer
  'возвращает ближайшую стандартную длину хвоста
  Dim iHvostik As Integer
  
  If bolKirp = False Then
    iHvostik = FormOptions.TextBoxHvostik
  Else
    iHvostik = FormOptions.TextBoxHvostikK
  End If
  
 If bolKirp = False Then
    If intLen < 575 Then
      If intLen < 525 Then
        If intLen < 475 Then
          If intLen < 425 Then
            If intLen > 200 Then
              GetNearStandartLenHvost = 400
            Else
              GetNearStandartLenHvost = iHvostik
            End If
          Else
            GetNearStandartLenHvost = 450
          End If
        Else
          GetNearStandartLenHvost = 500
        End If
      Else
        GetNearStandartLenHvost = 550
      End If
    Else
      If intLen >= 650 Then
        If intLen >= 750 Then
          If intLen >= 850 Then
            GetNearStandartLenHvost = 900
          Else
            GetNearStandartLenHvost = 800
          End If
        Else
          GetNearStandartLenHvost = 700
        End If
      Else
        GetNearStandartLenHvost = 600
      End If
    End If
  Else
    If intLen < 550 And intLen > iHvostik Then
      GetNearStandartLenHvost = 500
    ElseIf intLen >= 550 And intLen < 700 Then
      GetNearStandartLenHvost = 600
    ElseIf intLen >= 700 And intLen < 775 Then
      GetNearStandartLenHvost = 750
    ElseIf intLen >= 775 And intLen < 850 Then
      GetNearStandartLenHvost = 800
    ElseIf intLen >= 850 And intLen < 950 Then
      GetNearStandartLenHvost = 900
    ElseIf intLen >= 950 Then
      GetNearStandartLenHvost = 1000
    End If
  End If
  
End Function

Public Function SetBlockToListFromDrawing()
  Dim oBl As AcadBlock
  Dim oKar As clKarkas
  Dim oNumKandPlos As Num_PlosName
  Dim oBlAndMarkaK As BlockAndMarkaK
  Dim colK As Collection
  Dim colBlMarkaK As New Collection
  Dim sMarkaK As String
  Dim sType As String
  'Dim iNumK As Integer
  Dim i As Integer
  Dim j As Integer
  
  ListBoxBlocks.Clear
  For Each oBl In ThisDrawing.Blocks
    If InStr(oBl.Name, "К") Then
      Set oBlAndMarkaK = New BlockAndMarkaK
      Set oBlAndMarkaK.oBl = oBl
      colBlMarkaK.add oBlAndMarkaK
      'ListBoxBlocks.AddItem oBl.Name
    End If
  Next
  
  'заполняем столбец маркиК
  For Each oBlAndMarkaK In colBlMarkaK ' ListBoxBlocks.ListCount - 1
    Set oKar = New clKarkas
    If InStr(oBlAndMarkaK.oBl.Name, "П") = 0 Then 'ListBoxBlocks.List(i, 0)
      oKar.ObrabName GetFirstNamePlosKar(oBlAndMarkaK.oBl.Name) '(ListBoxBlocks.List(i, 0))
    Else
      oKar.ObrabName GetFirstNameProsKar(oBlAndMarkaK.oBl.Name) '(ListBoxBlocks.List(i, 0))
    End If
    Select Case oKar.strType
      Case "КД"
        Set colK = pcolPlosNumKD
      Case "КО"
        Set colK = pcolPlosNumKO
      Case "К"
        Set colK = pcolPlosNumK
    End Select
    'определяем имя марки
    If oKar.bolP = True Then
      sMarkaK = oKar.intP & "П" & oKar.strType
    Else
      sMarkaK = oKar.strType
    End If
  On Error Resume Next
    Set oNumKandPlos = colK.Item(oKar.strPlosKarName)
    If Err Then
  On Error GoTo 0
    Else
      'iNumK = oNumKandPlos.iNumK
      'sMarkaK = sMarkaK & iNumK
      oBlAndMarkaK.sType = oKar.strType
      oBlAndMarkaK.iNumK = oNumKandPlos.iNumK
      oBlAndMarkaK.sMarkaK = sMarkaK & oBlAndMarkaK.iNumK
      'ListBoxBlocks.List(i, 1) = sMarkaK
    End If
  Next
  
  'сортировка коллекции блоков с маркамиК по номерам марокК
  For i = 1 To colBlMarkaK.Count - 1
    For j = 1 To colBlMarkaK.Count - i
      If StrComp(colBlMarkaK(j).sType, colBlMarkaK(j + 1).sType) = 1 Then
        Set oBlAndMarkaK = colBlMarkaK(j)
        colBlMarkaK.Remove j
        colBlMarkaK.add oBlAndMarkaK, , , j
      ElseIf colBlMarkaK(j).iNumK > colBlMarkaK(j).iNumK Then
        Set oBlAndMarkaK = colBlMarkaK(j)
        colBlMarkaK.Remove j
        colBlMarkaK.add oBlAndMarkaK, , , j
      End If
    Next
  Next
  
  'заполняем листбокс
  i = 0
  For Each oBlAndMarkaK In colBlMarkaK
    ListBoxBlocks.AddItem oBlAndMarkaK.oBl.Name
    ListBoxBlocks.List(i, 1) = oBlAndMarkaK.sMarkaK
    i = i + 1
  Next
  
End Function

Public Function AddAtrMarkaKToBlock(oBl As AcadBlock)
  'проверяем есть ли у атрибута маркаК, если нет добавляем
  
  Dim oEnt As AcadEntity
  Dim oAtr As AcadAttribute
  Dim oAtrMarka As AcadAttribute
  Dim oAtrMarkaK As AcadAttribute
  Dim vPtMove As Variant

  Dim bolYes As Boolean
  
  For Each oEnt In oBl
    If TypeOf oEnt Is AcadAttribute Then
      If oEnt.TagString = "МаркаК" Then
        Set oAtrMarkaK = oEnt
        bolYes = True
      End If
      If oEnt.Layer = "Att~Marka" Then
        Set oAtrMarka = oEnt
        oAtrMarka.TextString = TextBoxMarka
      End If
    End If
  Next
  
  If bolYes = False Then
    'добавляем атрибут
    If Not oAtrMarka Is Nothing Then
      Set oAtr = oAtrMarka.Copy
      oAtr.Layer = "Каркасы"
      oAtr.TagString = "МаркаК"
      oAtr.PromptString = "МаркаК"
      oAtr.Lineweight = acLnWt025
      vPtMove = oAtrMarka.TextAlignmentPoint
      vPtMove(1) = vPtMove(1) - 375
      oAtrMarka.Move oAtrMarka.TextAlignmentPoint, vPtMove
    End If
  End If
  oAtrMarkaK.TextString = TextBoxMarkaK & TextBoxNomerK
  
  oBl.Reload
  
End Function

Private Function DefineNumK(oKar As clKarkas) As Integer
  'определение номера для плос каркаса
  Dim colK As Collection
  Dim oNumKandPlos As Num_PlosName
  Select Case oKar.strType
    Case "КД"
      Set colK = pcolPlosNumKD
    Case "КО"
      Set colK = pcolPlosNumKO
    Case "К"
      Set colK = pcolPlosNumK
  End Select
  
  'находим плоский какас в коллекции
On Error Resume Next
  Err.Clear
  Set oNumKandPlos = colK(oKar.strPlosKarName)
  If Err Then
    Err.Clear
On Error GoTo 0
    'находим минимальный свободный номер
    DefineNumK = GetMinNumKinColK(colK)
  Else
    DefineNumK = oNumKandPlos.iNumK
  End If
  
  If DefineNumK = 0 Then
    DefineNumK = 1
  End If
  
End Function

Private Function GetMinNumKinColK(colNumK As Collection) As Integer
  'находим минимальный свободный номер
  Dim oNumKandPlos As Num_PlosName
  Dim i As Integer
  
  'сортировка номеровК в колекциии
  Functions.SortyrNumKinColK colNumK
  
  If colNumK Is Nothing Then Exit Function
  For i = 1 To colNumK.Count
    If colNumK(i).iNumK > i Then
      'значит этот i не занят
      GetMinNumKinColK = i
      Exit Function
    End If
  Next
  GetMinNumKinColK = colNumK.Count + 1
End Function

Private Function ProvNumKinColKAndForm() As Boolean
  'проверка номерак для создаваемого блока
  Dim colK As Collection
  Dim oNumKandPlos As Num_PlosName
  Dim sVal As String
  Select Case objKar.strType
    Case "КД"
      Set colK = pcolPlosNumKD
    Case "КО"
      Set colK = pcolPlosNumKO
    Case "К"
      Set colK = pcolPlosNumK
  End Select
  
  If colK Is Nothing Then
    If Val(TextBoxNomerK) > 0 Then
      ProvNumKinColKAndForm = True
    End If
  Else
On Error Resume Next
    Set oNumKandPlos = colK(objKar.strPlosKarName)
    If Err Then
On Error GoTo 0
      'нет такого каркаса
      'проверяем есть ли номер из текстбокса в коллекции номеровК
      'этого номера быть не должно
      sVal = Functions.ProvNumKinColK(TextBoxNomerK, objKar.strType)
      If sVal <> "" Then
        MsgBox "Такой номер К уже есть для каркасов " & sVal, vbCritical, psVBProjectName
        ProvNumKinColKAndForm = False
        Exit Function
      End If
    Else
      'сверяем ноимера
      If Functions.ProvNumKinMarkaK(oNumKandPlos.iNumK, "", objKar.strType, TextBoxNomerK) = False Then
        MsgBox "Номер К=" & TextBoxNomerK & " не соответствует уже принятому номеру " & oNumKandPlos.iNumK & " для каркасов " & objKar.strPlosKarName, vbCritical, psVBProjectName
        ProvNumKinColKAndForm = False
        TextBoxNomerK = oNumKandPlos.iNumK
        Exit Function
      End If
    End If
  End If
  
End Function

Public Function GetAtrMarkaName() As String
  'определение значения для атрибута марки каркаса
  
'  If objKar.bolHeightRostInName = False Then
'    GetAtrMarkaName = objKar.strFirstName
'  Else
'    GetAtrMarkaName = objKar.strFirstName
'  End If
  
End Function

Attribute VB_Name = "FormOptions"
Attribute VB_Base = "0{34C196ED-0BE9-4E0A-9691-5CC7AE8995F5}{B117AE41-7530-4A97-9582-EF4DBC5198DD}"
Attribute VB_GlobalNameSpace = False
Attribute VB_Creatable = False
Attribute VB_PredeclaredId = True
Attribute VB_Exposed = False
Attribute VB_TemplateDerived = False
Attribute VB_Customizable = False
Option Explicit

Private Sub cmbCancel_Click()
  hide
End Sub

Private Sub cmbOK_Click()
  Dim sValue As String
  'записываем диаметры в ини
  iDiamVerhDef = TextBoxVerh
  iDiamNizDef = TextBoxNiz
  iDiamPopDef = TextBoxPop
  FileIni.WriteFile "Настройки", "Диаметр верхней арм", CStr(iDiamVerhDef)
  FileIni.WriteFile "Настройки", "Диаметр нижней арм", CStr(iDiamNizDef)
  FileIni.WriteFile "Настройки", "Диаметр поперечной арм", CStr(iDiamPopDef)
  FileIni.WriteFile "Настройки", "Высота ростверка", CStr(TextBoxHeightDef)
  'хвосты
  sValue = TextBoxHvost0 & ";" & TextBoxHvost1 & ";" & TextBoxHvost2 & ";" & TextBoxHvost3 & ";" & TextBoxHvost4 & ";" & TextBoxHvost5 & ";" & TextBoxHvost6 & ";" & TextBoxHvost7 & ";" & TextBoxHvost8 & ";" & TextBoxHvost9 & ";" & TextBoxHvostik & ";"
  FileIni.WriteFile "Настройка", "Хвосты", sValue
  sValue = TextBoxHvostK0 & ";" & TextBoxHvostK1 & ";" & TextBoxHvostK2 & ";" & TextBoxHvostK3 & ";" & TextBoxHvostK4 & ";" & TextBoxHvostK5 & ";" & TextBoxHvostK6 & ";" & TextBoxHvostK7 & ";" & TextBoxHvostK8 & ";" & TextBoxHvostK9 & ";" & TextBoxHvostikK & ";"
  FileIni.WriteFile "Настройка", "Хвосты-кирпичка", sValue
  hide
End Sub

Private Sub TextBoxHeightDef_Exit(ByVal Cancel As MSForms.ReturnBoolean)
  TextBoxHeightDef = CInt(Val(TextBoxHeightDef))
  If CInt(TextBoxHeightDef) < 400 Then
    MsgBox "Минимальная высота ростверка 400", vbCritical, psVBProjectName
    TextBoxHeightDef = 500
  End If
End Sub

Private Sub TextBoxNiz_Exit(ByVal Cancel As MSForms.ReturnBoolean)
  If Functions.ProvDiamStandard(TextBoxNiz) = False Then
    MsgBox TextBoxNiz & " - этот диаметр не поддерживается.", vbCritical, psVBProjectName
    TextBoxNiz = 10
  End If
End Sub

Private Sub TextBoxPop_Exit(ByVal Cancel As MSForms.ReturnBoolean)
  If Functions.ProvDiamStandard(TextBoxPop) = False Then
    MsgBox TextBoxPop & " - этот диаметр не поддерживается.", vbCritical, psVBProjectName
    TextBoxPop = 8
  End If
End Sub

Private Sub TextBoxVerh_Exit(ByVal Cancel As MSForms.ReturnBoolean)
  If Functions.ProvDiamStandard(TextBoxVerh) = False Then
    MsgBox TextBoxVerh & " - этот диаметр не поддерживается.", vbCritical, psVBProjectName
    TextBoxVerh = 12
  End If
End Sub

Attribute VB_Name = "Functions"
Option Explicit


Public Function GetLayer(strLayerName As String) As String
   'возвращает объект слоя, с заданным именем
   'если слоя с таким именем не было, он создается
   
   On Error GoTo HasError
   GetLayer = ThisDrawing.Layers.Item(strLayerName).Name

Exit Function

HasError:
   ThisDrawing.Layers.add (strLayerName)
   GetLayer = strLayerName
   
End Function

Public Function GetMacroFolder(strVBProjectName) As String
   'получение пути к корню макроса
   'без \
   
   Dim strMacroFolder As String
   Dim intValue As Integer
   
   On Error GoTo HasError
   
   strMacroFolder = Application.VBE.vbprojects.Item(strVBProjectName).FileName
   intValue = InStrRev(strMacroFolder, "\")
   strMacroFolder = Left(strMacroFolder, intValue - 1) 'корень с макросом, без \ на конце
   
   GetMacroFolder = strMacroFolder
   
Exit Function

HasError:
   Select Case Err.Number
      Case Else
         MsgBox "Functions, GetMacroFolder" & vbCrLf & _
               Err.Description, vbCritical, psVBProjectName
   End Select
   
End Function

Public Function GetNameWithoutExt(FileName As String) As String
   'возвращает имя файла без расширения ".dwg"
   
   Dim strExt As String
   
   strExt = LCase(Right(FileName, 4))
   If strExt = ".dwg" Then
      GetNameWithoutExt = Left(FileName, Len(FileName) - 4)
   End If
   
End Function

Public Function GetSelSet(strSelName As String) As AcadSelectionSet
   'возвращает набор, с заданным именем
   'если набор с таким именем был, он очищается
   
   On Error GoTo HasError
   Set GetSelSet = ThisDrawing.SelectionSets.Item(strSelName)
   GetSelSet.Clear
   
Exit Function

HasError:
   Set GetSelSet = ThisDrawing.SelectionSets.add(strSelName)
   
End Function

Public Function ProvDiamStandard(Diam As Integer) As Boolean
   Select Case Diam
      Case 8
         ProvDiamStandard = True
      Case 10
         ProvDiamStandard = True
      Case 12
         ProvDiamStandard = True
      Case 14
         ProvDiamStandard = True
      Case 16
         ProvDiamStandard = True
      Case 18
         ProvDiamStandard = True
      Case 20
         ProvDiamStandard = True
      Case 22
         ProvDiamStandard = True
      Case 25
         ProvDiamStandard = True
      Case 28
         ProvDiamStandard = True
      Case 32
         ProvDiamStandard = True
      Case 36
         ProvDiamStandard = True
      Case 40
         ProvDiamStandard = True
      Case Else
         ProvDiamStandard = False
   End Select
   
End Function

'Public Function GetNumHvosta(intLenHvosta As Integer) As Integer
'
'   If FormMain.CheckBoxKR.Value = False Then
'      Select Case intLenHvosta
'         Case 600
'            GetNumHvosta = 0
'         Case 400
'            GetNumHvosta = 1
'         Case 450
'            GetNumHvosta = 2
'         Case 500
'            GetNumHvosta = 3
'         Case 550
'            GetNumHvosta = 4
'         Case 700
'            GetNumHvosta = 5
'         Case 800
'            GetNumHvosta = 6
'         Case 900
'            GetNumHvosta = 7
'      End Select
'   Else
'      Select Case intLenHvosta
''         Case 600
''            GetNumHvosta = 0
'         Case 500
'            GetNumHvosta = 1
'         Case 600
'            GetNumHvosta = 2
'         Case 650
'            GetNumHvosta = 3
'         Case 750
'            GetNumHvosta = 4
'         Case 800
'            GetNumHvosta = 5
'         Case 900
'            GetNumHvosta = 6
'         Case 1000
'            GetNumHvosta = 7
'      End Select
'
'   End If
'End Function

Public Function ReturnLenHvosta(Nomer As Integer) As Integer
   
   If bolKirp = False Then
    Select Case Nomer
       Case 0
          ReturnLenHvosta = FormOptions.TextBoxHvost0
       Case 1
          ReturnLenHvosta = FormOptions.TextBoxHvost1
       Case 2
          ReturnLenHvosta = FormOptions.TextBoxHvost2
       Case 3
          ReturnLenHvosta = FormOptions.TextBoxHvost3
       Case 4
          ReturnLenHvosta = FormOptions.TextBoxHvost4
       Case 5
          ReturnLenHvosta = FormOptions.TextBoxHvost5
       Case 6
          ReturnLenHvosta = FormOptions.TextBoxHvost6
       Case 7
          ReturnLenHvosta = FormOptions.TextBoxHvost7
    End Select
   Else
    Select Case Nomer
'       Case 0
'          ReturnLenHvosta = 600
       Case 1
          ReturnLenHvosta = FormOptions.TextBoxHvostK1
       Case 2
          ReturnLenHvosta = FormOptions.TextBoxHvostK2
       Case 3
          ReturnLenHvosta = FormOptions.TextBoxHvostK3
       Case 4
          ReturnLenHvosta = FormOptions.TextBoxHvostK4
       Case 5
          ReturnLenHvosta = FormOptions.TextBoxHvostK5
       Case 6
          ReturnLenHvosta = FormOptions.TextBoxHvostK6
       Case 7
          ReturnLenHvosta = FormOptions.TextBoxHvostK7
    End Select
   End If
End Function

Public Function GetCorrectPath(sPath As String) As String
  
  If Right(sPath, 1) = "\" Then
    GetCorrectPath = Left(sPath, Len(sPath) - 1)
  Else
    GetCorrectPath = sPath
  End If
  
End Function

Public Function GetFieldHvostsFromString(sStringIni As String, bolKirpichka As Boolean)
  'заполнение полей формы Options значениями длин хвостов из строки
  Dim iVal As Integer
  Dim sVal As String
  Dim i As Integer
  Dim asVal() As String
  
  If sStringIni = "" Then Exit Function
  iVal = InStr(sStringIni, ";")
  
  If iVal = 0 Then Exit Function
  
    Do While iVal <> 0
      sVal = Left(sStringIni, iVal - 1)
      ReDim Preserve asVal(i)
      asVal(i) = sVal
      
      sStringIni = Mid(sStringIni, iVal + 1)
      iVal = InStr(sStringIni, ";")
      
      i = i + 1
    Loop
    
  On Error Resume Next
  If bolKirpichka = False Then
    FormOptions.TextBoxHvost0 = asVal(0)
    FormOptions.TextBoxHvost1 = asVal(1)
    FormOptions.TextBoxHvost2 = asVal(2)
    FormOptions.TextBoxHvost3 = asVal(3)
    FormOptions.TextBoxHvost4 = asVal(4)
    FormOptions.TextBoxHvost5 = asVal(5)
    FormOptions.TextBoxHvost6 = asVal(6)
    FormOptions.TextBoxHvost7 = asVal(7)
    FormOptions.TextBoxHvost8 = asVal(8)
    FormOptions.TextBoxHvost9 = asVal(9)
    FormOptions.TextBoxHvostik = asVal(10)
  Else
    FormOptions.TextBoxHvostK0 = asVal(0)
    FormOptions.TextBoxHvostK1 = asVal(1)
    FormOptions.TextBoxHvostK2 = asVal(2)
    FormOptions.TextBoxHvostK3 = asVal(3)
    FormOptions.TextBoxHvostK4 = asVal(4)
    FormOptions.TextBoxHvostK5 = asVal(5)
    FormOptions.TextBoxHvostK6 = asVal(6)
    FormOptions.TextBoxHvostK7 = asVal(7)
    FormOptions.TextBoxHvostK8 = asVal(8)
    FormOptions.TextBoxHvostK9 = asVal(9)
    FormOptions.TextBoxHvostikK = asVal(10)
  End If
  
End Function

Public Function ScanDrawToBlKarAndMarkaK()
  'сканирование чертежа и создание коллекции объектов имен_блоков с атрибутами маркиК
  
  Dim colNumK As Collection
  Dim colBlocksRef As New Collection
  Dim oNumKandPlos As Num_PlosName
  Dim oBlAndMarka As BlockAndMarkaK
  Dim oKar As clKarkas
  Dim selSet As AcadSelectionSet
  Dim oEnt As AcadEntity
  Dim oBlRef As AcadBlockReference
  Dim iCode(0) As Integer
  Dim vDate(0) As Variant
  Dim vAtr As Variant
  Dim sMarkaK As String
  Dim sMarka As String
  Dim sPlosKar As String
  Dim sTypePlosKar As String
  Dim sError As String
  Dim sVal As String
  Dim iNumK As Integer
  Dim bolAtrMarka  As Boolean
  Dim bolAtrMarkaK  As Boolean
  
  'Dim oBl As AcadBlock
  'Dim oKar As clKarkas
  'Dim oNumKandPlos As Num_PlosName
  Dim oBlAndMarkaK As BlockAndMarkaK
  Dim colK As Collection
  Dim colBlMarkaK As New Collection
  'Dim sMarkaK As String
  Dim sType As String
  'Dim iNumK As Integer
  Dim i As Integer
  Dim j As Integer
  
  'очищаем коллекции номеровК
  Set pcolPlosNumKD = Nothing
  Set pcolPlosNumKO = Nothing
  Set pcolPlosNumK = Nothing
  
  'фильтр блоков (правда вместе с хрефами и мн-блоками!!!)
  iCode(0) = 0: vDate(0) = "insert"
  
  Set selSet = Functions.GetSelSet("Блоки")
  'выбор на экране
  selSet.Select acSelectionSetAll, , , iCode, vDate
  
  For Each oEnt In selSet
    If TypeOf oEnt Is AcadBlockReference Then
      Set oBlRef = oEnt
      If oBlRef.HasAttributes = True Then
        If InStr(oBlRef.Name, "К") Then
          bolAtrMarka = False
          bolAtrMarkaK = False
          For Each vAtr In oBlRef.GetAttributes
            If vAtr.Layer = "Att~Marka" Then
              sMarka = vAtr.TextString
              bolAtrMarka = True
            End If
            If LCase(vAtr.TagString) = "маркак" Then
              sMarkaK = vAtr.TextString
              bolAtrMarkaK = True
            End If
          Next 'vAtr In oBlRef.GetAttributes
          
          If bolAtrMarka = True And bolAtrMarkaK = True Then
            
            'добавляем блок в коллекцию блоков каркасов чертежа
            Set oBlAndMarka = New BlockAndMarkaK
            Set oBlAndMarka.oBl = oBlRef
            oBlAndMarka.sAtrMarka = sMarka
            On Error Resume Next
            colBlMarkaK.add oBlAndMarka, sMarka
            'colBlocksRef.add oBlAndMarka, sMarka
            On Error GoTo 0
            
            'если уже определен номер для этого плоского каркаса
            Set oKar = New clKarkas
            If InStr(oBlRef.Name, "П") = 0 Then
              oKar.ObrabName GetFirstNameKar(sMarka, False)
            Else
              oKar.ObrabName GetFirstNameKar(sMarka, True)
            End If
            sPlosKar = oKar.strPlosKarName
            sTypePlosKar = oKar.strType
            
            Set oNumKandPlos = ProvPlosKarInColNumK(sPlosKar, sTypePlosKar)
            
            If oNumKandPlos Is Nothing Then
              'нет номера для этого плоского каркаса, добавляем
              'определение номера для каркаса
              iNumK = GetNumFromMarkaK(sMarkaK, sTypePlosKar)
              If iNumK = 0 Or iNumK = 10000 Then
                'добавляем блок в коллекцию блоков с ошибочными маркамиК
                If iNumK = 10000 Then
                  sError = "Неверный тип К в имени маркиК."
                Else
                  sError = "Неопределен порядковый номер в имени маркиК."
                End If
                AddBlToColBadMarkak sError, oBlRef
              Else
                'проверка наличия номераК в коллекции
                sVal = ProvNumKinColK(iNumK, sTypePlosKar)
                If sVal <> "" Then
                  'добавляем блок в кол плохих имен марокК
                  sError = "Номер К из имени маркиК уже определен для другого каркаса - " & sVal
                  AddBlToColBadMarkak sError, oBlRef
                 ' AddBlToColBadMarkak sError, oNumKandPlos.colBl(1)
                Else
                  'добаляем маркуК в коллекцию марокК и имен плоских карксов
                  AddNumKAndPlosKar iNumK, sPlosKar, sTypePlosKar, oBlRef
                End If
              End If
            Else 'уже есть такой плос кар в кол номеров плос каркасов
              'проверяем номер с номером в маркеК блока
              If ProvNumKinMarkaK(oNumKandPlos.iNumK, sMarkaK, sTypePlosKar, , oBlRef, oNumKandPlos.colBl(1)) = True Then
                'добавляем блок в коллекцию блоков с таким номеромК плоского каркаса
                AddNumKAndPlosKar oNumKandPlos.iNumK, sPlosKar, sTypePlosKar, oBlRef
              Else
                'обрабатывается в самой проверяющей функции ProvNumKinMarkaK
              End If
            End If 'oNumKAndPlos Is Nothing
          End If 'bolAtrMarka = True And bolAtrMarkaK = True
          
        End If 'InStr(oBlRef.Name, "К")
      End If 'oBlRef.HasAttributes = True
    End If 'TypeOf oEnt Is AcadBlockReference
  Next 'oEnt In selSet
  
  'сортировка номеровК в коллекции
  SortyrNumKinColK pcolPlosNumKD
  SortyrNumKinColK pcolPlosNumKO
  SortyrNumKinColK pcolPlosNumK
  
  'проверяем есть ли пропущенные номера
  Dim sFreeNumKinColKD As String
  Dim sFreeNumKinColKO As String
  Dim sFreeNumKinColK As String
  Dim sMessage As String
  sFreeNumKinColKD = ProvFreeNumK(pcolPlosNumKD)
  sFreeNumKinColKO = ProvFreeNumK(pcolPlosNumKO)
  sFreeNumKinColK = ProvFreeNumK(pcolPlosNumK)
  If sFreeNumKinColKD <> "" Then
    sMessage = "Пропущены номера К в каркасах типа КД: " & sFreeNumKinColKD & vbCrLf
  End If
  If sFreeNumKinColKO <> "" Then
    sMessage = sMessage & "Пропущены номера К в каркасах типа КО: " & sFreeNumKinColKO & vbCrLf
  End If
  If sFreeNumKinColK <> "" Then
    sMessage = sMessage & "Пропущены номера К в каркасах типа К: " & sFreeNumKinColK
  End If
  If sMessage <> "" Then
    MsgBox sMessage, vbInformation, psVBProjectName
  End If
  
  'если есть блоки с ошибочными маркамиК выводим форму сними
  If pcolBadMarkaKBl.Count <> 0 Then
    
    FormBadBlMarkaK.Show vbModeless
  End If
  
  
'  For Each oBlAndMarka In colBlocksRef
'    'If InStr(oBlRef.Name, "К") Then
'      Set oBlAndMarkaK = New BlockAndMarkaK
'      Set oBlAndMarkaK.oBl = oBlAndMarka.oBl
'      oBlAndMarkaK.sAtrMarka = oBlAndMarka.sAtrMarka
'      colBlMarkaK.add oBlAndMarkaK
'      'ListBoxBlocks.AddItem oBl.Name
'    'End If
'  Next
  
  For Each oBlAndMarkaK In colBlMarkaK ' ListBoxBlocks.ListCount - 1
    Set oKar = New clKarkas
    If InStr(oBlAndMarkaK.sAtrMarka, "П") = 0 Then  'ListBoxBlocks.List(i, 0)
      oKar.ObrabName GetFirstNameKar(oBlAndMarkaK.sAtrMarka, False) '(ListBoxBlocks.List(i, 0))
    Else
      oKar.ObrabName GetFirstNameKar(oBlAndMarkaK.sAtrMarka, True) '(ListBoxBlocks.List(i, 0))
    End If
    Select Case oKar.strType
      Case "КД"
        Set colK = pcolPlosNumKD
      Case "КО"
        Set colK = pcolPlosNumKO
      Case "К"
        Set colK = pcolPlosNumK
    End Select
    'определяем имя марки
    If oKar.bolP = True Then
      sMarkaK = oKar.intP & "П" & oKar.strType
    Else
      sMarkaK = oKar.strType
    End If
  On Error Resume Next
    Set oNumKandPlos = colK.Item(oKar.strPlosKarName)
    If Err Then
  On Error GoTo 0
    Else
      'iNumK = oNumKandPlos.iNumK
      'sMarkaK = sMarkaK & iNumK
      oBlAndMarkaK.sType = oKar.strType
      oBlAndMarkaK.iNumK = oNumKandPlos.iNumK
      oBlAndMarkaK.sMarkaK = sMarkaK & oBlAndMarkaK.iNumK
      'ListBoxBlocks.List(i, 1) = sMarkaK
    End If
  Next
  
  'сортировка коллекции блоков с маркамиК по номерам марокК
  For i = 1 To colBlMarkaK.Count - 1
    For j = 1 To colBlMarkaK.Count - i
      If StrComp(colBlMarkaK(j).sType, colBlMarkaK(j + 1).sType) = 1 Then
        Set oBlAndMarkaK = colBlMarkaK(j)
        colBlMarkaK.Remove j
        colBlMarkaK.add oBlAndMarkaK, , , j
      ElseIf StrComp(colBlMarkaK(j).sType, colBlMarkaK(j + 1).sType) = 0 Then
        If colBlMarkaK(j).iNumK > colBlMarkaK(j + 1).iNumK Then
          Set oBlAndMarkaK = colBlMarkaK(j)
          colBlMarkaK.Remove j
          colBlMarkaK.add oBlAndMarkaK, , , j
        End If
      End If
    Next
  Next
  
  'заполняем листбокс
  FormMain.ListBoxBlocks.Clear
  i = 0
  For Each oBlAndMarkaK In colBlMarkaK
    FormMain.ListBoxBlocks.AddItem oBlAndMarkaK.sAtrMarka, i
    FormMain.ListBoxBlocks.List(i, 1) = oBlAndMarkaK.sMarkaK
    i = i + 1
  Next
  
End Function

Private Function GetNumFromMarkaK(sMarkaK As String, sType As String) As Integer
  'определение номера к из МаркиК, предпологая что тип = sType
  '10000-неправильное имя маркиК, тип К не верный
  Dim iVal As Integer
  
  iVal = InStr(sMarkaK, sType)
  If iVal = 0 Then
    GetNumFromMarkaK = 10000
    Exit Function
  End If
  
  GetNumFromMarkaK = Val(Mid(sMarkaK, iVal + Len(sType)))
  
End Function

Private Function AddBlToColBadMarkak(sError As String, Optional oBlRef As AcadBlockReference)
  'добавление блока в коллекцию блоков с ошиибочной маркойК
  Dim oBadMarkaKBl As New BadMarkaKBl
  oBadMarkaKBl.sError = sError
  Set oBadMarkaKBl.oBlRef = oBlRef
  On Error Resume Next
  pcolBadMarkaKBl.add oBadMarkaKBl, CStr(oBlRef.ObjectID)
  On Error GoTo 0
End Function

Public Function AddNumKAndPlosKar(iNumK As Integer, sNamePlosKar As String, sType As String, Optional oBl As AcadBlockReference)
  'добавление объекта в коллекцию номеровК и имен плос каркасов
  Dim oNumKandPlos As New Num_PlosName
  Dim colK As Collection
  oNumKandPlos.sPlosKar = sNamePlosKar
  oNumKandPlos.iNumK = iNumK
  If Not oBl Is Nothing Then
    oNumKandPlos.colBl.add oBl
  End If
  
  Select Case sType
    Case "КД"
      Set colK = pcolPlosNumKD
    Case "КО"
      Set colK = pcolPlosNumKO
    Case "К"
      Set colK = pcolPlosNumK
  End Select
On Error Resume Next
  colK.add oNumKandPlos, sNamePlosKar
  If Err Then
On Error GoTo 0
    If Not oBl Is Nothing Then
      Set oNumKandPlos = colK(sNamePlosKar)
      oNumKandPlos.colBl.add oBl
    End If
  End If
End Function

Public Function ProvNumKinColK(iNumK As Integer, sType As String) As String
  'проверка наличия номераК в кол номеровК
  Dim colK As Collection
  Dim oNumKandPlos As Num_PlosName
  Select Case sType
    Case "КД"
      Set colK = pcolPlosNumKD
    Case "КО"
      Set colK = pcolPlosNumKO
    Case "К"
      Set colK = pcolPlosNumK
  End Select
  For Each oNumKandPlos In colK
    If oNumKandPlos.iNumK = iNumK Then
      ProvNumKinColK = oNumKandPlos.sPlosKar
      Exit Function
    End If
  Next
End Function

Private Function ProvPlosKarInColNumK(sPlosName As String, sType As String) As Num_PlosName
  'проверка есть ли уже такой каркс в коллекции
  Dim colK As Collection
  Select Case sType
    Case "КД"
      Set colK = pcolPlosNumKD
    Case "КО"
      Set colK = pcolPlosNumKO
    Case "К"
      Set colK = pcolPlosNumK
  End Select
  On Error Resume Next
  Err.Clear
  Set ProvPlosKarInColNumK = colK(sPlosName)
  If Err Then
    Err.Clear
    Set ProvPlosKarInColNumK = Nothing
  End If
  On Error GoTo 0
End Function

Public Function ProvNumKinMarkaK(iNumK As Integer, sMarkaK As String, sType As String, Optional iNumKinMark As Integer, Optional oBl As AcadBlockReference, Optional oBlOprNum As AcadBlockReference) As Boolean
  'проверяем номер с номером в маркеК блока
  Dim iNumKinMarkaK As Integer
  Dim sError As String
  
  If iNumKinMark = 0 Then
    iNumKinMarkaK = GetNumFromMarkaK(sMarkaK, sType)
  Else
    iNumKinMarkaK = iNumKinMark
  End If
  
  'добавляем блок в коллекцию блоков с ошибочными маркамиК
  If iNumKinMarkaK = 0 Or iNumKinMarkaK = 10000 Then
    If iNumKinMarkaK = 10000 Then
      sError = "Неверный тип К в имени маркиК."
    Else
      sError = "Неопределен порядковый номер в имени маркиК."
    End If
    If Not oBl Is Nothing Then
      AddBlToColBadMarkak sError, oBl
    End If
    If Not oBlOprNum Is Nothing Then
      AddBlToColBadMarkak sError, oBlOprNum
    End If
    
    ProvNumKinMarkaK = False
    Exit Function
  End If
  
  'сверяем номераК
  If iNumK <> iNumKinMarkaK Then
    If iNumKinMark = 0 Then
      sError = "Номер К=" & iNumKinMarkaK & " в маркеК не совпадает с определнным номером " & iNumK & " для этого плоского каркаса."
      If Not oBl Is Nothing Then
        AddBlToColBadMarkak sError, oBl
      End If
      If Not oBlOprNum Is Nothing Then
        AddBlToColBadMarkak sError, oBlOprNum
      End If
    End If
    ProvNumKinMarkaK = False
  Else
    ProvNumKinMarkaK = True
  End If
End Function

Public Function SortyrNumKinColK(colK As Collection)
  'сортировка номеровК в колекциии
  Dim oNumKandPlos As Num_PlosName
  Dim iCount As Integer
  Dim i As Integer
  Dim j As Integer
  
  If colK Is Nothing Then Exit Function
  For i = 1 To colK.Count - 1
    For j = 1 To colK.Count - i
      If colK(j).iNumK > colK(j + 1).iNumK Then
        Set oNumKandPlos = colK(j)
        colK.Remove (j)
        colK.add oNumKandPlos, oNumKandPlos.sPlosKar, , j
      End If
    Next
  Next
  
End Function

Public Function ProvFreeNumK(colK As Collection) As String
  'пароверка пропущенных номеров в коллекции номеров к
  'возвращает строку пропущенных номеров через зпт,
  Dim oNumKandPlos As Num_PlosName
  Dim iFreeNumK As Integer
  Dim i As Integer
  
  If colK Is Nothing Then Exit Function
  For i = 1 To colK.Count - 1
    If colK(i + 1).iNumK - colK(i).iNumK > 1 Then
      'пропущен номер(а)
      iFreeNumK = colK(i).iNumK + 1
      ProvFreeNumK = ProvFreeNumK & iFreeNumK & ","
      Do While colK(i + 1).iNumK - (iFreeNumK + 1) > 1
        iFreeNumK = iFreeNumK + 1
        ProvFreeNumK = ProvFreeNumK & iFreeNumK & ","
      Loop
    End If
  Next
  
  If ProvFreeNumK <> "" Then
    ProvFreeNumK = Left(ProvFreeNumK, Len(ProvFreeNumK) - 1)
  End If
  
End Function

Public Function GetFirstNameProsKar(BlName As String) As String
  'имя каркаса, все что после "-" в нижнем регистре
  
  Dim intValue As Integer
  Dim strValue As String
  
  intValue = InStr(BlName, "-")
   'оставшаяся строка до "-"
   If intValue = 0 Then
     GetFirstNameProsKar = UCase(BlName)
   Else
   'переводим все что после "-" в нижний регистр
      strValue = LCase(Mid(BlName, intValue + 1))
      'имя до "-"
      GetFirstNameProsKar = UCase(Left(BlName, intValue))
      'полное имя каркаса
      GetFirstNameProsKar = GetFirstNameProsKar & strValue
   End If
End Function

Public Function GetFirstNameKar(BlName As String, bolProsKar As Boolean) As String
  'имя плоского каркаса, все что после "-" в нижнем регистре, без (шт.2)
  Dim intValue As Integer
  Dim strValue As String
  
  intValue = InStr(BlName, "-")
   'оставшаяся строка до "-"
  If intValue = 0 Then
     GetFirstNameKar = BlName
  Else
    'переводим все что после "-" в нижний регистр
    strValue = LCase(Mid(BlName, intValue + 1))
    'имя до "-"
    GetFirstNameKar = UCase(Left(BlName, intValue))
    'полное имя каркаса
    GetFirstNameKar = GetFirstNameKar & strValue
  End If
  
'  If bolProsKar = False Then
'    intValue = InStr(LCase(BlName), "(шт.")
'    If intValue <> 0 Then
'      FormMain.objKar.intKolShtuk = Val(Mid(BlName, intValue + 4))
'      'отбрасываем то что в скобках
'      GetFirstNameKar = (Left(BlName, intValue - 1))
'    Else
'      FormMain.objKar.intKolShtuk = 1
'    End If
'  End If
  
  'если задана высота ростверка (6)
  'intValue = inStr(LCase(BlName), "(")
  'If intValue <> 0 Then
  If GetFirstNameKar Like "*([1-9]*" Then
    intValue = InStr(GetFirstNameKar, "(")
    If intValue <> 0 Then
      FormMain.objKar.bolHeightRostInName = True
      FormMain.objKar.intHeightRost = Val(Mid(GetFirstNameKar, intValue + 1)) * 100
'      'отбрасываем то что в скобках
'      GetFirstNameKar = (Left(BlName, intValue - 1))
    End If
  Else
    FormMain.objKar.bolHeightRostInName = False
    FormMain.objKar.intHeightRost = FormOptions.TextBoxHeightDef
  End If
  
End Function

Public Function GetKolShtukPlosKar(BlName As String) As Integer
  'определяем кол-во штук плоских каркасов в блоке (шт.2)
  
  Dim intValue As Integer
  Dim dValue As Double
  
  intValue = InStr(LCase(BlName), "(шт.")
  If intValue = 0 Then
    GetKolShtukPlosKar = 1
  Else
    dValue = Val(Mid(BlName, intValue + 4))
    intValue = dValue
    If intValue <> dValue Then
      'ошибка определения кол-ва плоских каркасов
      GetKolShtukPlosKar = 0
    Else
      GetKolShtukPlosKar = intValue
    End If
  End If
End Function

Public Function GetMassaDiamPM(intDiam As Integer) As Double
'определение массы 1м.п. арматуры

   Select Case intDiam
      Case 6
         GetMassaDiamPM = 0.222
      Case 8
         GetMassaDiamPM = 0.395
      Case 10
         GetMassaDiamPM = 0.617
      Case 12
         GetMassaDiamPM = 0.888
      Case 14
         GetMassaDiamPM = 1.208
      Case 16
         GetMassaDiamPM = 1.578
      Case 18
         GetMassaDiamPM = 1.998
      Case 20
         GetMassaDiamPM = 2.466
      Case 22
         GetMassaDiamPM = 2.984
      Case 25
         GetMassaDiamPM = 3.85
      Case 28
         GetMassaDiamPM = 4.83
      Case 32
         GetMassaDiamPM = 6.31
      Case 36
         GetMassaDiamPM = 7.99
      Case 40
         GetMassaDiamPM = 9.87
   End Select
   
End Function

Attribute VB_Name = "Main"
Option Explicit
   
'Процедура вставки(создания) блока каркаса по заданному имени
   
   Public Const psVBProjectName As String = "MakeKarkas"
   
   Public FileIni As New ClassINI
   Public iDiamVerhDef As Integer
   Public iDiamNizDef As Integer
   Public iDiamPopDef As Integer
   'значения полей параметров караса
   Public sTBMarka As String
   Public iTBDiamVerh As Integer
   Public iTBDiamNiz As Integer
   Public iTBDiamPop As Integer
   Public iTBLenHvostLeft As Integer
   Public iTBLenHvostFight As Integer
   Public iTBRabLen As Integer
   Public iTBKolShtuk As Integer
   
   'коллекции номеров каркасов маркиК для кирпички
   Public pcolPlosNumK As New Collection
   Public pcolPlosNumKO As New Collection
   Public pcolPlosNumKD As New Collection
   'коллекция с ошибочыми марками К
   Public pcolBadMarkaKBl As New Collection
   
   Type Path
      Path As String
      FilesDwg() As String
      IsFiles As Boolean
   End Type
   
   Type FileBlock
      Path As String
      FilesDwg As String
   End Type
   
   Enum eType
      KD = 0
      KO = 1
      K = 2
   End Enum
   
   Public bolKirp As Boolean


Public Sub Main()
      
'   On Error GoTo HasError
  ' On Error Resume Next
   bolKirp = False
   FormMain.Show
   
Exit Sub
'HasError:
'   MsgBox Err.Description, vbCritical
End Sub

Public Sub MainK()
      
  ' On Error GoTo HasError
'   On Error Resume Next
   bolKirp = True
   FormMain.Show
   
Exit Sub
HasError:
   MsgBox Err.Description, vbCritical
End Sub

Attribute VB_Name = "Num_PlosName"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'номер К и соответствующее ему имя плоского каркаса
Public iNumK As Integer
Public sPlosKar As String
Public colBl As New Collection

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Option Explicit

Public Sub test()
   Dim strFolder As String
   Dim intP As Integer
   Dim strP As String
   
   strFolder = "6П,7П,9П,12П,16П,17П_КД"
   intP = 16
   
   strP = GetFolderWithП(intP, strFolder)
   
End Sub

Private Function GetFolderWithП(intП As Integer, Folder As String) As String
   'поиск папки в библиотеке с таким кол-вом П (5П,7П, и т.д.)
   'возвращает полный путь к папке
   
   Dim intVal As Integer
   
   intVal = InStr(Folder, intП & "П")
   
   
End Function




Public Sub test0()
  Dim sValue As String
  sValue = "КО"
  
  If sValue <> "КО" Then
    MsgBox "Ни куя себе!!!!!!!!!"
  End If
  
End Sub

Attribute VB_Name = "clKarkas"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'класс описывающий пространственный каркас
   
   Public strBlName As String 'входное имя каркаса
   
   'доступные поля
   Public strMarkaK As String 'марка по типу 6ПК1
   Public strMarkaKPlos As String 'марка плос кар по типу К1
   Public strType As String 'тип каркаса КО, КД, К
   Public strError As String 'текст ошибки если она есть
   Public strPrim As String 'примечание (может пригодится)
   Public strFirstName As String 'входное имя каркаса
   Public strPlosKarName As String 'имя плос каркаса (всё! что после П)
   Public bolP As Boolean 'простр.каркас
   Public intN As Integer 'кол-во n
   Public intP As Integer 'кол-во плоских каркасов
   Public intLenRab As Integer 'рабочая длина каркаса = n*150
   Public intKolKar As Integer 'кол-во каркасов (с учетом (шт.2), для плоских каркасов)
   Public intKolShtuk As Integer
   Public sNSech As String 'номер сечения
   Public intLenSech As Integer 'ширина сечения
   Public intHeightRost As Integer 'высота ростверка
   Public bolHeightRostInName As Boolean 'признак заданной высоты ростверка в названии (в скобках) каркаса,  (6)
   Public sShifrProsKar As String 'шифр листа пространственного каркаса
   Public sShifrPlosKar As String 'шифр листа плоского каркаса
   Public bolObrabotan As Boolean 'признак обработки каркаса, галочка (т.е. нажали применить для него)
   Public bolD As Boolean 'признак наличия доп.попер.стержня
   Public intShagDopPopSter As Integer 'шаг доп. поп. стержня
   Public intHvostLeft As Integer 'длина левого хвоста
   Public intHvostRight As Integer 'длина правого хвоста
   Public intCenterVerhArm As Integer 'расст от верха роств до центра верхней продол арм
   Public intCenterNizArm As Integer 'расст от низа роств до центра нижней продол арм
   Public dMassaProsKar As Double 'масса пространственного каркаса
   Public dMassaPlosKar As Double 'масса плоского каркаса
   'продольная арматура
   Public intDiamVerhArm As Integer 'диаметр верх арм
   Public intDiamNizArm As Integer 'диам нижней арм
   Public intLenProdolArm As Integer 'длина продольной арматуры
   Public sKlassVerhArm As String 'класс верхней арматуры ("A-III")
   Public sKlassNizArm As String 'класс нижней арматуры
   Public sGOSTVerhArm As String 'норматив.док. верхней арматуры ("ГОСТ 5781-82")
   Public sGOSTNizArm As String 'норматив.док. нижней арматуры
   Public dMassaEdVerhSter As Double 'масса одного верхнего стержня
   Public dMassaEdNizSter As Double 'масса одного нижнего стержня
   Public sNaimVerhArm As String 'наименование верх арм
   Public sNaimNizArm As String 'наименование нижней арм
   'поперечная арматура
   Public intDiamPopArm As Integer 'диаметр поперечной арм
   Public intLenPopArm As Integer 'длина поперечной арматуры
   Public intShagPopArm As Integer 'шаг поперечной арм
   Public sKlassPopArm As String 'класс поперечной арматуры
   Public sGOSTPopArm As String 'норматив.док. поперечной арматуры
   Public intKolPopSterPlosKar As Integer 'кол-во поперечных стержней в плоском каркасе
   Public dMassaEdPopSter As Double 'масса одного поперечного стержня
   Public sNaimPopArm As String 'наименование поперечного арм
   'связевая арматура
   Public intLenSvyzArm As Integer 'длина связевой арматуры
   Public intDiamSvyzVerhArm As Integer 'диаметр связевой верхней арматуры
   Public intDiamSvyzNizArm As Integer 'диаметр связевой нижней арматуры
   Public intShagSvyzVerhArm As Integer 'шаг связевой верхней арматуры
   Public intShagSvyzNizArm As Integer 'шаг связевой нижней арматуры
   Public intKolSvyzVerhSter As Integer 'кол связевой верхней арматуры
   Public intKolSvyzNizSter As Integer 'кол связевой нижней арматуры
   Public sKlassSvyzVerhArm As String 'класс связевой верхней арматуры
   Public sKlassSvyzNizArm As String 'класс связевой нижней нарматуры
   Public sGOSTSvyzVerhArm As String 'норматив.док. связевой верхней арматуры
   Public sGOSTSvyzNizArm As String 'норматив.док. связевой нижней арматуры
   Public dMassaEdSvyzVerhSter As Double 'масса одного связевого верхнего стержня
   Public dMassaEdSvyzNizSter As Double 'масса одного связевого нижнего стержня
   Public sNaimSvyzNizArm As String 'наименование связевого нижнего арм
   Public sNaimSvyzVerhArm As String 'наименование связевого верхнего арм
   'параметры для усиления (масса будет обрабатываться в классе доп.стержней)
   Public bolUsilenie As Boolean 'признак наличия усиления
   Public intUsLen As Integer 'ширина усиливыаемого сечения
   Public intUsDiamVerhArm As Integer 'диаметр верхних усиливающих стержней
   Public intUsDiamNizArm As Integer 'диаметр нижних усиливающих стержней
   Public intUsShagVerhArm As Integer 'шаг верхних усиливающих стержней
   Public intUsShagNizArm As Integer 'шаг нижних усиливающих стержней
   Public sUsKlassVerhArm As String 'класс верхней усиливающей арматуры
   Public sUsKlassNizArm As String 'класс нижней усиливающей арматуры
   Public sUsGOSTVerhArm As String 'норм.док. верхней усиливающей арматуры
   Public sUsGOSTNizArm As String 'норм.док. нижней усиливающей арматуры
   
'имя каркаса для сортировки
Public Property Get Name() As String
  Name = strFirstName
End Property
'Public Property Let Name(ByVal vNewValue As String)
'
'   Dim intValue As Integer
'   Dim strValue As String
'   Dim strNameVal As String
'
'   strBlName = vNewValue
'
'   ObrabName strBlName
'
'   'начальное значение кол-ва каркасов(блоков на чертеже)
'   intKolKar = 1
'
'   'имя блока
'   strBlName = vNewValue
'
'   strFirstName = Functions.GetFirstNameProsKar(strBlName)
   
'   intValue = InStr(strFirstName, "-")
'   'оставшаяся строка до "-"
'   If intValue <> 0 Then
'      strNameVal = Left(strFirstName, intValue - 1)
'   Else
'      'если есть скобки то отбрасываем их пока
'      intValue = InStr(strFirstName, "(")
'      If intValue = 0 Then
'        strNameVal = strFirstName
'      Else
'        strNameVal = Left(strFirstName, intValue - 1)
'      End If
'   End If
'
'   'по полученному имени определяем тип каркаса и все остальное
'
'   'кол-во плоских каркасов ("5П45КД" - 5 плоских каркасиков)
'   intP = Val(strNameVal)
'   'номер П в имени каркаса
'   intValue = InStr(LCase(strNameVal), "п")
'   'имя после П
'   strNameVal = Right(strNameVal, Len(strNameVal) - intValue)
'
'   'определяем раб длину L= n*150
'   intN = Val(strNameVal)
'   intLenRab = intN * 150
'   If intLenRab = 0 Then
'      strError = "Рабочая длина каркаса (n*150) - не определена. "
'      Exit Property
'   End If
'
'   intValue = InStr(LCase(strNameVal), "к")
'   'оставшаяся строка после "к"
'   strNameVal = Right(strNameVal, Len(strNameVal) - intValue)
'
'   'после "к" может стоять или "О","Д", или ничего
'   strValue = LCase(Mid(strNameVal, 1, 1))
'
'   If strValue = "о" Then
'      strType = "КО"
'      strValue = Right(strNameVal, Len(strNameVal) - 1)
'      If Len(strValue) > 1 Then
'         strError = "После КО может быть максимум одна цифра. "
'         Exit Property
'      End If
'   ElseIf strValue = "д" Then
'      strType = "КД"
'      strValue = Right(strNameVal, Len(strNameVal) - 1)
'      If Len(strValue) > 2 Then
'         strError = "После КД может быть максимум две цифры. "
'         Exit Property
'      End If
'   ElseIf strValue = "" Then
'      strType = "К"
'   Else
'      strError = "После К стоит недопустимый символ. "
'   End If
'   'определяем длину хвостов
'   Select Case strType
'      Case "КД"
'         intHvostLeft = ReturnLenHvosta(Val(Left(strValue, 1)))
'         intHvostRight = ReturnLenHvosta(Val(Right(strValue, 1)))
'      Case "КО"
'         intHvostLeft = 20
'         intHvostRight = ReturnLenHvosta(Val(Left(strValue, 1)))
'      Case "К"
'         intHvostLeft = 20
'         intHvostRight = 20
'   End Select
'
'   If intHvostLeft = 0 Or intHvostRight = 0 Then
'      strError = "Длина хвостов не определена. "
'      Exit Property
'   End If
'
'   'длина продольной арматуры
'   intLenProdolArm = intLenRab + intHvostLeft + intHvostRight
'
'   'проверяем то что после "-"
'
'   intValue = InStr(strFirstName, "-")
'   'оставшаяся строка после "-"
'   strNameVal = Right(strFirstName, Len(strFirstName) - intValue)
'   'если есть скобки то отбрасываем их пока
'   intValue = InStr(strNameVal, "(")
'   If intValue <> 0 Then
'      strNameVal = Left(strNameVal, intValue - 1)
'   End If
'
'   If InStr(strNameVal, "д") <> 0 Then
'      bolD = True
'   End If
'
'   intValue = InStr(strNameVal, "в")
'   If intValue = 0 Then
'      'диаметр по-умолчанию
'      intDiamVerhArm = FormSpecRost.TextBoxDiamVerhArmDef
'   Else
'      'после "в" может быть "н", или цифра
'      If Mid(strNameVal, intValue + 1, 1) Like "[1-9]" Then
'         'если цифра
'         intDiamVerhArm = ReturnDiamStandard(Val(Right(strNameVal, Len(strNameVal) - intValue)))
'      Else
'         'если не цифра
'         intDiamVerhArm = ReturnDiamStandard(Val(Right(strNameVal, Len(strNameVal) - (intValue + 1))))
'      End If
'      If intDiamVerhArm = 0 Then
'         strError = "Диаметр верхней арматуры не определен. "
'         Exit Property
'      End If
'   End If
'   intValue = InStr(strNameVal, "н")
'   If intValue = 0 Then
'      intDiamNizArm = FormSpecRost.TextBoxDiamNizArmDef
'   Else
'      'после "н" может быть только цифра
'      If Mid(strNameVal, intValue + 1, 1) Like "[1-9]" Then
'         intDiamNizArm = ReturnDiamStandard(Val(Right(strNameVal, Len(strNameVal) - intValue)))
'      End If
'      If intDiamNizArm = 0 Then
'         strError = "Диаметр нижней арматуры не определен. "
'         Exit Property
'      End If
'   End If
'
'   intValue = InStr(strNameVal, "п")
'   If intValue = 0 Then
'      intDiamPopArm = FormSpecRost.TextBoxDiamPopArmDef
'   Else
'      'после "н" может быть только цифра
'      If Mid(strNameVal, intValue + 1, 1) Like "[1-9]" Then
'         intDiamPopArm = ReturnDiamStandard(Val(Right(strNameVal, Len(strNameVal) - intValue)))
'      End If
'      If intDiamPopArm = 0 Then
'         strError = "Диаметр поперечной арматуры не определен. "
'         Exit Property
'      End If
'   End If
'
'   'проверяем если есть скобки (6) - высота ростверка
'   intValue = InStr(strFirstName, "(")
'   If intValue <> 0 Then
'      'определяем кол-во
'      intValue = Val(Mid(strFirstName, intValue + 1))
'      If intValue <> 0 Then
'        intHeightRost = intValue * 100
'        bolHeightRostInName = True
'      Else
'        strPrim = "Непонятно что в скобках!"
'      End If
'   End If
'
'End Property



Private Function ReturnDiamStandard(Diam As Integer) As Integer
   'проверка соответствия входного диаметра списку стандартных диаметров арматуры
      
   Select Case Diam
      Case 6
         ReturnDiamStandard = Diam
      Case 8
         ReturnDiamStandard = Diam
      Case 10
         ReturnDiamStandard = Diam
      Case 12
         ReturnDiamStandard = Diam
      Case 14
         ReturnDiamStandard = Diam
      Case 16
         ReturnDiamStandard = Diam
      Case 18
         ReturnDiamStandard = Diam
      Case 20
         ReturnDiamStandard = Diam
      Case 22
         ReturnDiamStandard = Diam
      Case 25
         ReturnDiamStandard = Diam
      Case 28
         ReturnDiamStandard = Diam
      Case 32
         ReturnDiamStandard = Diam
      Case 36
         ReturnDiamStandard = Diam
      Case 40
         ReturnDiamStandard = Diam
      Case Else
         ReturnDiamStandard = 0
   End Select
   
End Function

Public Sub ObrabParam()
  'обработка введенных параметров каркаса
  'расчет массы
  Dim intVal As Integer
  
  On Error Resume Next
  
  If strError <> "" Then Exit Sub
  
  'определяем рабочую длину каркаса
  If bolD = True Then
    intLenRab = intLenRab + intShagDopPopSter
    'кол-во поперечных стержней
    intKolPopSterPlosKar = intN + 2
  Else
    'кол-во поперечных стержней
    intKolPopSterPlosKar = intN + 1
  End If
  
  'длина продольной арматуры
  intLenProdolArm = intLenRab + intHvostLeft + intHvostRight
  
  'единичная масса верхнего стержня кг
  dMassaEdVerhSter = Functions.GetMassaDiamPM(intDiamVerhArm) * intLenProdolArm / 1000
  'единичная масса нижнего стержня кг
  dMassaEdNizSter = Functions.GetMassaDiamPM(intDiamNizArm) * intLenProdolArm / 1000
  'длина поперечного стержня (расст между продол арм + по 25 выпуски)
  intLenPopArm = intHeightRost - intCenterNizArm - intCenterVerhArm + 50
  'единичная масса поперечного стержня кг
  dMassaEdPopSter = Functions.GetMassaDiamPM(intDiamPopArm) * intLenPopArm / 1000
  'масса плоского каркаса
  dMassaPlosKar = dMassaEdVerhSter + dMassaEdNizSter + dMassaEdPopSter * intKolPopSterPlosKar
    
  'для простр.кркасов расчитываем связевую арматуру
  If bolP = True Then
    'длина связевой арм
    If bolKirp = False Then
      intLenSvyzArm = intLenSech - 20
    Else
      intLenSvyzArm = intLenSech - 70
    End If
    'ед.масса связевого стержня
    dMassaEdSvyzNizSter = Functions.GetMassaDiamPM(intDiamSvyzNizArm) * intLenSvyzArm / 1000
    dMassaEdSvyzVerhSter = Functions.GetMassaDiamPM(intDiamSvyzVerhArm) * intLenSvyzArm / 1000
    'кол-во связевых верхних стержней
    intKolSvyzVerhSter = intLenRab \ intShagSvyzVerhArm + 1 'деление нацело
    intVal = intLenRab Mod intShagSvyzVerhArm
    If intVal > 25 Then intKolSvyzVerhSter = intKolSvyzVerhSter + 1
    'кол-во связевых нижних стержней
    intKolSvyzNizSter = intLenRab \ intShagSvyzNizArm + 1 'деление нацело
    intVal = intLenRab Mod intShagSvyzNizArm
    If intVal > 25 Then intKolSvyzNizSter = intKolSvyzNizSter + 1
    'масса простран.каркаса
    dMassaProsKar = intP * dMassaPlosKar + dMassaEdSvyzNizSter * intKolSvyzNizSter + dMassaEdSvyzVerhSter * intKolSvyzVerhSter
  End If
  
  'наименовыания для стержней
  sNaimVerhArm = intDiamVerhArm & "-" & sKlassVerhArm & " " & sGOSTVerhArm & " L=" & intLenProdolArm
  sNaimNizArm = intDiamNizArm & "-" & sKlassNizArm & " " & sGOSTNizArm & " L=" & intLenProdolArm
  sNaimPopArm = intDiamPopArm & "-" & sKlassPopArm & " " & sGOSTPopArm & " L=" & intLenPopArm
  sNaimSvyzVerhArm = intDiamSvyzVerhArm & "-" & sKlassSvyzVerhArm & " " & sGOSTSvyzVerhArm & " L=" & intLenSvyzArm
  sNaimSvyzNizArm = intDiamSvyzNizArm & "-" & sKlassSvyzNizArm & " " & sGOSTSvyzNizArm & " L=" & intLenSvyzArm
  
  If Err Then
    strError = Err.Description
    Err.Clear
  End If
  
End Sub

Public Function ObrabName(sFirstNameProsKar As String)
  'способ посимвольной обработки имени простр каркаса
  'пример марки каркаса 4П41КД-вн22п10(6)
  
  Dim i As Integer
'  Dim strFirstName As String
  Dim sValue As String
  Dim iValue As Integer
  Dim Value As Variant
  Dim aValue As Variant
  Dim sDoTire As String
  Dim sPosleTire As String
  
 ' strBlName = sFirstNameProsKar
  iValue = InStr(sFirstNameProsKar, "(")
  If iValue = 0 Then
    strFirstName = sFirstNameProsKar
  Else
    strFirstName = Left(sFirstNameProsKar, iValue - 1)
  End If
  
  strError = ""
  
  'начальное значение кол-ва каркасов(блоков на чертеже)
   intKolKar = 1
    
  'все что после "-"
  iValue = InStr(strFirstName, "-")
  If iValue <> 0 Then
    sPosleTire = Mid(strFirstName, iValue + 1)
    sDoTire = Left(strFirstName, iValue - 1)
  Else
    'нет "-"
    sDoTire = strFirstName
  End If
  
  'до тире "-"
  iValue = InStr(sDoTire, "П")
  If iValue <> 0 Then
    bolP = True
    'разделяем строку по П
    aValue = Split(sDoTire, "П")
    If UBound(aValue) <> 1 Then
      strError = "Ошибка при разделении строки имени каркаса по П."
      Exit Function
    End If
    iValue = Val(aValue(0))
    If aValue(0) <> iValue Or iValue = 0 Or iValue > 99 Then
      strError = "Кол-во плоских каркасов не определено."
      Exit Function
    End If
    'кол-во плоских каркасов
    intP = iValue
    'имя плоского каркаса
    If sPosleTire = "" Then
      strPlosKarName = aValue(1)
    Else
      strPlosKarName = aValue(1) & "-" & sPosleTire
    End If
  Else
    'плоский каркас
    strPlosKarName = strFirstName
    'кол-во плоских каркасов
    intP = 1
    bolP = False
  End If
  
  'разделяем по К имя плоского каркаса до тире
  iValue = InStr(strPlosKarName, "-")
  If iValue <> 0 Then
    'имя плоского каркаса до тире
    sValue = Left(strPlosKarName, iValue - 1)
  Else
    sValue = strPlosKarName
  End If
  aValue = Split(sValue, "К")
  If UBound(aValue) <> 1 Then
    strError = "Ошибка при разделении строки имени каркаса по К."
    Exit Function
  End If
  iValue = Val(aValue(0))
  If aValue(0) <> iValue Or iValue < 2 Or iValue > 99 Then
    strError = "Кол-во n*150 не определено."
    Exit Function
  End If
  'кол-во n (n*150)
  intN = iValue
  intLenRab = intN * 150
  If aValue(1) = "" Then
    'значит тип каркаса К
    strType = "К"
    If bolKirp = False Then
      intHvostRight = FormOptions.TextBoxHvostik
      intHvostLeft = FormOptions.TextBoxHvostik
    Else
      intHvostRight = FormOptions.TextBoxHvostikK
      intHvostLeft = FormOptions.TextBoxHvostikK
    End If
  Else
    'первый символ после К
    sValue = Left(aValue(1), 1)
    If sValue = "Д" Then
      strType = "КД"
      'определяем хвосты
      Value = Val(Mid(aValue(1), 2))
      iValue = Value
      If iValue <> Value Or iValue > 99 Then
        strError = "Хвосты не определены."
        Exit Function
      End If
      If iValue < 10 Then
        intHvostRight = Functions.ReturnLenHvosta(iValue) ' pclOptions.GetLenHvosta(iValue)
        intHvostLeft = Functions.ReturnLenHvosta(0) 'pclOptions.GetLenHvosta(0)
      Else
        sValue = Right(aValue(1), 2)
        iValue = Left(sValue, 1)
        intHvostRight = Functions.ReturnLenHvosta(iValue) 'pclOptions.GetLenHvosta(iValue)
        iValue = Right(sValue, 1)
        intHvostLeft = Functions.ReturnLenHvosta(iValue) 'pclOptions.GetLenHvosta(iValue)
      End If
    ElseIf sValue = "О" Then
      strType = "КО"
      'определяем хвост
      Value = Val(Mid(aValue(1), 2))
      iValue = Value
      If iValue <> Value Or iValue > 9 Then
        strError = "Хвосты не определены."
        Exit Function
      End If
      intHvostRight = Functions.ReturnLenHvosta(iValue) 'pclOptions.GetLenHvosta(iValue)
      If bolKirp = False Then
        intHvostLeft = FormOptions.TextBoxHvostik
      Else
        intHvostLeft = FormOptions.TextBoxHvostikK
      End If
    Else
      strError = "Тип каркаса не определен."
      Exit Function
    End If
  End If
  
  'обрабатываем строку после "-"
  If sPosleTire = "" Then
    'стандартные диаметры
    intDiamVerhArm = iDiamVerhDef ' pclOptions.piDiamKarVerhDef
    intDiamNizArm = iDiamNizDef 'pclOptions.piDiamKarNizDef
    intDiamPopArm = iDiamPopDef 'pclOptions.piDiamKarPopDef
  Else
    iValue = InStr(sPosleTire, "в")
    If iValue <> 0 Then
      'определяем диаметры верхней
      sValue = Mid(sPosleTire, iValue + 1, 1)
      If sValue = "н" Then
        Value = Val(Mid(sPosleTire, iValue + 2))
      Else
        Value = Val(Mid(sPosleTire, iValue + 1))
      End If
      iValue = Value
      If iValue <> Value Or ProvDiamStandard(iValue) = False Then
        strError = "Не определен диаметр верхней арматуры."
        Exit Function
      End If
      intDiamVerhArm = iValue
    Else
      'стандартный верхний диаметр
      intDiamVerhArm = iDiamVerhDef ' pclOptions.piDiamKarVerhDef
    End If
    iValue = InStr(sPosleTire, "н")
    If iValue <> 0 Then
      Value = Val(Mid(sPosleTire, iValue + 1))
      iValue = Value
      If iValue <> Value Or ProvDiamStandard(iValue) = False Then
        strError = "Не определен диаметр нижней арматуры."
        Exit Function
      End If
      intDiamNizArm = iValue
    Else
      'стандартный нижний диаметр
      intDiamNizArm = iDiamNizDef 'pclOptions.piDiamKarNizDef
    End If
    iValue = InStr(sPosleTire, "п")
    If iValue <> 0 Then
      Value = Val(Mid(sPosleTire, iValue + 1))
      iValue = Value
      If iValue <> Value Or ProvDiamStandard(iValue) = False Then
        strError = "Не определен диаметр поперечной арматуры."
        Exit Function
      End If
      intDiamPopArm = iValue
    Else
      'стандартный поперечный диаметр
      intDiamPopArm = iDiamPopDef ' pclOptions.piDiamKarPopDef
    End If
    iValue = InStr(sPosleTire, "д")
    If iValue <> 0 Then
      'есть доп.поп.стер.
      bolD = True
      If bolKirp = True Then
        Value = Val(Mid(sPosleTire, iValue + 1))
        iValue = Value
        If iValue <> Value Then
          strError = "Не определен шаг доп.поп.стержня."
          Exit Function
        End If
        If iValue <> 0 Then
          intShagDopPopSter = iValue * 10
          
          'втрой вариет Д, если Д больше 150, записываем в текстбокс
          If intShagDopPopSter > 150 Then
            FormMain.TextBoxD = intShagDopPopSter
          End If
        Else
          intShagDopPopSter = 100
        End If
      Else
        intShagDopPopSter = 100
      End If
      intLenRab = intLenRab + intShagDopPopSter
    Else
      bolD = False
    End If
  End If 'sPosleTire <> "" Then
  
  'проверяем если есть скобки (6) - высота ростверка
  Dim dValue As Double
   iValue = InStr(sFirstNameProsKar, "(")
   If iValue <> 0 Then
      'определяем кол-во
      dValue = Val(Mid(sFirstNameProsKar, iValue + 1))
      If dValue <> 0 Then
        intHeightRost = dValue * 100
        bolHeightRostInName = True
        strPlosKarName = strPlosKarName & "(" & dValue & ")"
      Else
        strPrim = "Неопределено что в скобках (высота ростверка)!"
        bolHeightRostInName = False
      End If
   End If
   
  'марка плос кар типа К1
  If strMarkaK <> "" Then
    iValue = InStr(strMarkaK, "(")
    If iValue <> 0 Then
      sValue = Left(strMarkaK, iValue - 1)
    Else
      sValue = strMarkaK
    End If
    If bolP = True Then
      iValue = InStr(sValue, "П")
      If iValue <> 0 Then
        If Val(sValue) <> intP Then
          strError = "МаркаК не соответствует марке пространственного каркаса."
          Exit Function
        End If
        strMarkaKPlos = Mid(sValue, iValue + 1)
      End If
    Else
      strMarkaKPlos = strMarkaK
    End If
  End If
  
End Function

Attribute VB_Name = "clKarkas_star"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'   Enum eType
'      KD = 0
'      KO = 1
'      K = 2
'   End Enum

'параметры каркаса, определяемые по имени

   Dim strName As String
   Public strFirstName As String 'полное имя каркаса с правильным регистром
   Public strNameBezShtuk As String 'имя до (шт.2)
   Public strMarkaKarkasa As String 'имя до (шт.2)
   Public strPlosKarName As String
   Public bolП As Boolean
   Public intP As Integer
   Public intLenRab As Integer
   Public strError As String
   
   Public intDiamVerh As Integer
   Public intDiamNiz As Integer
   Public intDiamPop As Integer
   Public intHvostLeft As Integer
   Public intHvostRight As Integer
   Public intN As Integer
   Public bolD As Boolean
   Public strType As String 'КО, КД, К
   Public intKolShtuk As Integer 'кол штук (шт.2)
   
      
Public Property Get Name() As String
   Name = strName
End Property
Public Property Let Name(ByVal vNewValue As String)
   
   Dim intValue As Integer
   Dim strValue As String
   Dim strValue2 As String
   Dim strNameVal As String
   Dim strNamePlosKar As String
   Dim intType As Integer
   
   strName = vNewValue
   
   strError = ""
   bolП = False
   intLenRab = 0
   strFirstName = ""
   intDiamVerh = 0
   intDiamNiz = 0
   intDiamPop = 0
   intHvostLeft = 0
   intHvostRight = 0
   intN = 0
   bolD = False
   strType = ""
   intKolShtuk = 0
   
   ObrabName vNewValue
   
'
'   strName = vNewValue
'
'   intValue = InStr(strName, "-")
'   'оставшаяся строка до "-"
'   If intValue <> 0 Then
'      'переводим все что после "-" в нижний регистр
'      strValue = LCase(Mid(strName, intValue + 1))
'      strValue2 = UCase(Left(strName, intValue))
'      strName = strValue2 & strValue
'      strNameVal = Left(strName, intValue - 1)
'      strFirstName = strValue2 & strValue
'   Else
'      strNameVal = UCase(strName)
'      strFirstName = strNameVal
'   End If
'
'   'если есть скобки то отбрасываем их пока
'   intValue = InStr(strNameVal, "(")
'   If intValue <> 0 Then
'      strNameVal = Left(strNameVal, intValue - 1)
'   End If
'
'   'по полученному имени определяем тип каркаса и все остальное
'
'   'пространственный каркас, Да/Нет
'   intValue = InStr(LCase(strNameVal), "п")
'   If intValue = 0 Then
'      bolП = False
'   Else
'      bolП = True
'   End If
'
'   strNameVal = Right(strNameVal, Len(strNameVal) - intValue)
'   strNamePlosKar = strNameVal
'
'   'определяем раб длину L= n*150
'   intN = Val(strNameVal)
'   intLenRab = intN * 150
'   If intLenRab = 0 Then
'      strError = "Рабочая длина каркаса (n*150) - не определена. "
'      Exit Property
'   End If
'
'   intValue = InStr(LCase(strNameVal), "к")
'   'оставшаяся строка после "к"
'   strNameVal = Right(strNameVal, Len(strNameVal) - intValue)
'
'   'после "к" может стоять или "О","Д", или ничего
'   strValue = LCase(Mid(strNameVal, 1, 1))
'
'   If strValue = "о" Then
'      intType = eType.KO
'      strType = "КО"
'      strValue = Right(strNameVal, Len(strNameVal) - 1)
'      If Len(strValue) > 1 Then
'         strError = "После КО может быть максимум одна цифра. "
'         Exit Property
'      End If
'   ElseIf strValue = "д" Then
'      intType = eType.KD
'      strType = "КД"
'      strValue = Right(strNameVal, Len(strNameVal) - 1)
'      If Not Len(strValue) = 2 And Not Len(strValue) = 0 Then
'         strError = "После КД может быть пусто или две цифры. "
'         Exit Property
'      End If
'   ElseIf strValue = "" Then
'      intType = eType.K
'      strType = "К"
'   Else
'      strError = "После К стоит недопустимый символ. "
'   End If
'   'определяем длину хвостов
'   Select Case intType
'      Case eType.KD
'         intHvostLeft = ReturnLenHvosta(Val(Left(strValue, 1)))
'         intHvostRight = ReturnLenHvosta(Val(Right(strValue, 1)))
'      Case eType.KO
'         intHvostLeft = 20
'         intHvostRight = ReturnLenHvosta(Val(Left(strValue, 1)))
'      Case eType.K
'         intHvostLeft = 20
'         intHvostRight = 20
'   End Select
'
'   If intHvostLeft = 0 Or intHvostRight = 0 Then
'      strError = "Длина хвостов не определена. "
'   End If
'
'   'проверяем то что после "-"
'
'   intValue = InStr(strName, "-")
'   'оставшаяся строка после "-"
'   strNameVal = Right(strName, Len(strName) - intValue)
'   'если есть скобки то отбрасываем их пока
'   intValue = InStr(strNameVal, "(")
'   If intValue <> 0 Then
'      strNameVal = Left(strNameVal, intValue - 1)
'   End If
'
'   If InStr(strNameVal, "д") <> 0 Then
'      bolD = True
'      intLenRab = intLenRab + 100
'   End If
'
'   intValue = InStr(strNameVal, "в")
'   If intValue = 0 Then
'      intDiamVerh = 12
'   Else
'      'после "в" может быть "н", или цифра
'      If Mid(strNameVal, intValue + 1, 1) Like "[1-9]" Then
'         'если цифра
'         intDiamVerh = ReturnDiamStandard(Val(Right(strNameVal, Len(strNameVal) - intValue)))
'      Else
'         'если не цифра
'         intDiamVerh = ReturnDiamStandard(Val(Right(strNameVal, Len(strNameVal) - (intValue + 1))))
'      End If
'      If intDiamVerh = 0 Then
'         strError = "Диаметр верхней арматуры не определен. "
'         Exit Property
'      End If
'   End If
'   intValue = InStr(strNameVal, "н")
'   If intValue = 0 Then
'      intDiamNiz = 10
'   Else
'      'после "н" может быть только цифра
'      If Mid(strNameVal, intValue + 1, 1) Like "[1-9]" Then
'         intDiamNiz = ReturnDiamStandard(Val(Right(strNameVal, Len(strNameVal) - intValue)))
'      End If
'      If intDiamNiz = 0 Then
'         strError = "Диаметр нижней арматуры не определен. "
'         Exit Property
'      End If
'   End If
'
'   intValue = InStr(strNameVal, "п")
'   If intValue = 0 Then
'      intDiamPop = 8
'   Else
'      'после "н" может быть только цифра
'      If Mid(strNameVal, intValue + 1, 1) Like "[1-9]" Then
'         intDiamPop = ReturnDiamStandard(Val(Right(strNameVal, Len(strNameVal) - intValue)))
'      End If
'      If intDiamPop = 0 Then
'         strError = "Диаметр поперечной арматуры не определен. "
'         Exit Property
'      End If
'   End If
'
'   'проверяем если есть скобки
'   intValue = InStr(LCase(strName), "(шт.")
'   If intValue <> 0 Then
'      If bolП = True Then
'        strError = "В марке простр.каркаса не может быть (шт.)"
'        Exit Property
'      End If
'      strNameBezShtuk = Left(strFirstName, intValue - 1)
''      If InStr(LCase(strName), "(шт.") = 0 Then
''         strError = "Неопределено то что в скобках! " & vbCrLf & _
''                  "Кол-во плоских каркасов записывается так: (шт.2) "
''         Exit Property
''      Else
'         'определяем кол-во
'         intKolShtuk = Val(Mid(strName, intValue + 4))
'         If intKolShtuk = 0 Then
'            strError = "Неопределено кол-во каркасов! "
'            Exit Property
'         End If
''      End If
'      If intKolShtuk <> 0 And bolП = True Then
'         strError = "В пространственном каркасе не может быть установлено кол-во (шт." & intKolShtuk & ")! "
'         Exit Property
'      End If
'   End If
''   'имя каркаса без (шт.2)
''   If intValue = 0 Then
''      strFirstName = strName
''   Else
''      strFirstName = Left(strName, intValue - 1)
''   End If
'
'   If intKolShtuk = 0 Then intKolShtuk = 1
   
End Property

'Пространственный каркас, ДА/Нет
Public Property Get П() As Boolean
   П = bolП
End Property

'Раб длина L=n*150
Public Property Get LenRab() As Integer
   LenRab = intLenRab
End Property

'ошибка при обработке имени каркаса
Public Property Get Error() As String
   Error = strError
End Property


Private Function ReturnLenHvosta(Nomer As Integer) As Integer
   
   If bolKirp = False Then
    Select Case Nomer
       Case 0
          ReturnLenHvosta = FormOptions.TextBoxHvost0
       Case 1
          ReturnLenHvosta = FormOptions.TextBoxHvost1
       Case 2
          ReturnLenHvosta = FormOptions.TextBoxHvost2
       Case 3
          ReturnLenHvosta = FormOptions.TextBoxHvost3
       Case 4
          ReturnLenHvosta = FormOptions.TextBoxHvost4
       Case 5
          ReturnLenHvosta = FormOptions.TextBoxHvost5
       Case 6
          ReturnLenHvosta = FormOptions.TextBoxHvost6
       Case 7
          ReturnLenHvosta = FormOptions.TextBoxHvost7
    End Select
   Else
    Select Case Nomer
'       Case 0
'          ReturnLenHvosta = 600
       Case 1
          ReturnLenHvosta = FormOptions.TextBoxHvostK1
       Case 2
          ReturnLenHvosta = FormOptions.TextBoxHvostK2
       Case 3
          ReturnLenHvosta = FormOptions.TextBoxHvostK3
       Case 4
          ReturnLenHvosta = FormOptions.TextBoxHvostK4
       Case 5
          ReturnLenHvosta = FormOptions.TextBoxHvostK5
       Case 6
          ReturnLenHvosta = FormOptions.TextBoxHvostK6
       Case 7
          ReturnLenHvosta = FormOptions.TextBoxHvostK7
    End Select
  End If
End Function

Private Function ReturnDiamStandard(Diam As Integer) As Integer
   'проверка соответствия входного диаметра списку стандартных диаметров арматуры
      
   Select Case Diam
      Case 8
         ReturnDiamStandard = Diam
      Case 10
         ReturnDiamStandard = Diam
      Case 12
         ReturnDiamStandard = Diam
      Case 14
         ReturnDiamStandard = Diam
      Case 16
         ReturnDiamStandard = Diam
      Case 18
         ReturnDiamStandard = Diam
      Case 20
         ReturnDiamStandard = Diam
      Case 22
         ReturnDiamStandard = Diam
      Case 25
         ReturnDiamStandard = Diam
      Case 28
         ReturnDiamStandard = Diam
      Case 32
         ReturnDiamStandard = Diam
      Case 36
         ReturnDiamStandard = Diam
      Case 40
         ReturnDiamStandard = Diam
      Case Else
         ReturnDiamStandard = 0
   End Select
   
End Function

Private Function ObrabName(sBlKarName As String)
  'способ посимвольной обработки имени простр каркаса
  'пример марки каркаса 4П41КД-вн22п10(6)
  
  Dim i As Integer
'  Dim strFirstName As String
  Dim sValue As String
  Dim iValue As Integer
  Dim Value As Variant
  Dim aValue As Variant
'  Dim strPlosKarName As String
  Dim sDoTire As String
  Dim sPosleTire As String
  
  strError = ""
    
  'все что после "-" переводим в нижний регистр
  iValue = InStr(sBlKarName, "-")
  If iValue <> 0 Then
    sPosleTire = LCase(Mid(sBlKarName, iValue + 1))
    sDoTire = UCase(Left(sBlKarName, iValue - 1))
    strFirstName = sDoTire & "-" & sPosleTire
  Else
    'все что в скобках в нижний регистр
    iValue = InStr(sBlKarName, "(")
    If iValue <> 0 Then
      sPosleTire = LCase(Mid(sBlKarName, iValue))
      sDoTire = UCase(Left(sBlKarName, iValue - 1))
      strFirstName = sDoTire & sPosleTire
    Else
      sDoTire = UCase(sBlKarName)
      strFirstName = sDoTire
    End If
  End If
  
  iValue = InStr(strFirstName, "П")
  If iValue <> 0 Then
    bolП = True
    strPlosKarName = Mid(strFirstName, iValue + 1)
    strMarkaKarkasa = strFirstName
    intKolShtuk = 1
    'обрабатываем то что после "-"
    
    'разделяем строку по П
    aValue = Split(strFirstName, "П")
    If UBound(aValue) <> 1 Then
      strError = "Ошибка при разделении строки имени каркаса по П."
      Exit Function
    End If
    iValue = Val(aValue(0))
    If aValue(0) <> iValue Or iValue = 0 Or iValue > 99 Then
      strError = "Кол-во плоских каркасов не определено."
      Exit Function
    End If
    strPlosKarName = aValue(1)
    'кол-во плоских каркасов
    intP = iValue
  Else
    'плоский каркас
    intP = 1
    iValue = InStr(strFirstName, "(шт.")
    If iValue = 0 Then
      intKolShtuk = 1
      strMarkaKarkasa = strFirstName
    Else
      intKolShtuk = Val(Mid(strFirstName, iValue + 4))
      If intKolShtuk = 0 Then
        strError = "Кол-во каркасов не определено."
        Exit Function
      End If
'      strFirstName = Left(strFirstName, iValue - 1)
      strMarkaKarkasa = Left(strFirstName, iValue - 1)
    End If
    strPlosKarName = strMarkaKarkasa
  End If
  
  'разделяем по К
  iValue = InStr(strPlosKarName, "-")
  If iValue <> 0 Then
    'имя плоского каркаса до тире
    sValue = Left(strPlosKarName, iValue - 1)
  Else
    sValue = strPlosKarName
  End If
  aValue = Split(sValue, "К")
  If UBound(aValue) <> 1 Then
    strError = "Ошибка при разделении строки имени каркаса по К."
    Exit Function
  End If
  iValue = Val(aValue(0))
  If aValue(0) <> iValue Or iValue < 5 Or iValue > 99 Then
    strError = "Кол-во n*150 не определено."
    Exit Function
  End If
  'кол-во n (n*150)
  intN = iValue
  If aValue(1) = "" Then
    'значит тип каркаса К
    strType = "К"
    intHvostRight = 20
    intHvostLeft = 20
  Else
    'первый символ после К
    sValue = Left(aValue(1), 1)
    If sValue = "Д" Then
      strType = "КД"
      'определяем хвосты
      Value = Val(Mid(aValue(1), 2))
      iValue = Value
      If iValue <> Value Or iValue > 99 Then
        strError = "Хвосты не определены."
        Exit Function
      End If
      If iValue < 10 Then
        intHvostRight = ReturnLenHvosta(iValue)
        intHvostLeft = ReturnLenHvosta(0)
      Else
        sValue = Right(aValue(1), 2)
        iValue = Left(sValue, 1)
        intHvostRight = ReturnLenHvosta(iValue)
        iValue = Right(sValue, 1)
        intHvostLeft = ReturnLenHvosta(iValue)
      End If
      If intHvostLeft = 0 Or intHvostRight = 0 Then
        strError = "Хвосты 0 длины."
        Exit Function
      End If
    ElseIf sValue = "О" Then
      strType = "КО"
      'определяем хвост
      Value = Val(Mid(aValue(1), 2))
      iValue = Value
      If iValue <> Value Or iValue > 9 Then
        strError = "Хвосты не определены."
        Exit Function
      End If
      intHvostRight = ReturnLenHvosta(iValue)
      intHvostLeft = 20
    Else
      strError = "Тип каркаса не определен."
      Exit Function
    End If
    If intHvostRight = 0 Then
        strError = "Хвост 0 длины."
        Exit Function
    End If
  End If
  
  'обрабатываем строку после "-"
'  If sPosleTire <> "" Then
    iValue = InStr(sPosleTire, "в")
    If iValue <> 0 Then
      'определяем диаметры верхней
      sValue = Mid(sPosleTire, iValue + 1, 1)
      If sValue = "н" Then
        Value = Val(Mid(sPosleTire, iValue + 2))
      Else
        Value = Val(Mid(sPosleTire, iValue + 1))
      End If
      iValue = Value
      If iValue <> Value Or ProvDiamStandard(iValue) = False Then
        strError = "Не определен диаметр верхней арматуры."
        Exit Function
      End If
      intDiamVerh = iValue
    Else
      'стандартный верхний диаметр
      intDiamVerh = iDiamVerhDef
    End If
    iValue = InStr(sPosleTire, "н")
    If iValue <> 0 Then
      Value = Val(Mid(sPosleTire, iValue + 1))
      iValue = Value
      If iValue <> Value Or ProvDiamStandard(iValue) = False Then
        strError = "Не определен диаметр нижней арматуры."
        Exit Function
      End If
      intDiamNiz = iValue
    Else
      'стандартный нижний диаметр
      intDiamNiz = iDiamNizDef
    End If
    iValue = InStr(sPosleTire, "п")
    If iValue <> 0 Then
      Value = Val(Mid(sPosleTire, iValue + 1))
      iValue = Value
      If iValue <> Value Or ProvDiamStandard(iValue) = False Then
        strError = "Не определен диаметр поперечной арматуры."
        Exit Function
      End If
      intDiamPop = iValue
    Else
      'стандартный поперечный диаметр
      intDiamPop = iDiamPopDef
    End If
    iValue = InStr(sPosleTire, "д")
    If iValue <> 0 Then
      'есть доп.поп.стер.
      bolD = True
      intLenRab = intN * 150 + 100
    Else
      bolD = False
      intLenRab = intN * 150
    End If
'  End If 'sPosleTire <> "" Then
  
  Dim intHeightRost As Integer
  Dim bolHeightRostInName As Boolean
  
  'проверяем если есть скобки (6) - высота ростверка
  If bolП = True Then
   iValue = InStr(strFirstName, "(")
   If iValue <> 0 Then
      'определяем кол-во
      iValue = Val(Mid(strFirstName, iValue + 1))
      If iValue <> 0 Then
         intHeightRost = iValue * 100
         bolHeightRostInName = True
      Else
        strError = "Высота ростверка не определена (в скобках)!"
      End If
   End If
  End If
End Function

Public Function ProvDiamStandard(Diam As Integer) As Boolean
   Select Case Diam
      Case 8
         ProvDiamStandard = True
      Case 10
         ProvDiamStandard = True
      Case 12
         ProvDiamStandard = True
      Case 14
         ProvDiamStandard = True
      Case 16
         ProvDiamStandard = True
      Case 18
         ProvDiamStandard = True
      Case 20
         ProvDiamStandard = True
      Case 22
         ProvDiamStandard = True
      Case 25
         ProvDiamStandard = True
      Case 28
         ProvDiamStandard = True
      Case 32
         ProvDiamStandard = True
      Case 36
         ProvDiamStandard = True
      Case 40
         ProvDiamStandard = True
      Case Else
         ProvDiamStandard = False
   End Select
   
End Function

Public Sub ObrabParam()
  'обработка введенных параметров каркаса
  'расчет массы
  Dim intVal As Integer
  
  On Error Resume Next
  
  If strError <> "" Then Exit Sub
  
  'определяем рабочую длину каркаса
  If bolD = True Then
    intLenRab = intLenRab + intShagDopPopSter
    'кол-во поперечных стержней
    intKolPopSterPlosKar = intN + 2
  Else
    'кол-во поперечных стержней
    intKolPopSterPlosKar = intN + 1
  End If
  
  'длина продольной арматуры
  intLenProdolArm = intLenRab + intHvostLeft + intHvostRight
  
  'единичная масса верхнего стержня кг
  dMassaEdVerhSter = Functions.GetMassaDiamPM(intDiamVerhArm) * intLenProdolArm / 1000
  'единичная масса нижнего стержня кг
  dMassaEdNizSter = Functions.GetMassaDiamPM(intDiamNizArm) * intLenProdolArm / 1000
  'длина поперечного стержня (расст между продол арм + по 25 выпуски)
  intLenPopArm = intHeightRost - intCenterNizArm - intCenterVerhArm + 50
  'единичная масса поперечного стержня кг
  dMassaEdPopSter = Functions.GetMassaDiamPM(intDiamPopArm) * intLenPopArm / 1000
  'масса плоского каркаса
  dMassaPlosKar = dMassaEdVerhSter + dMassaEdNizSter + dMassaEdPopSter * intKolPopSterPlosKar
    
  'для простр.кркасов расчитываем связевую арматуру
  If bolP = True Then
    'длина связевой арм
    intLenSvyzArm = intLenSech - 20
    'ед.масса связевого стержня
    dMassaEdSvyzNizSter = Functions.GetMassaDiamPM(intDiamSvyzNizArm) * intLenSvyzArm / 1000
    dMassaEdSvyzVerhSter = Functions.GetMassaDiamPM(intDiamSvyzVerhArm) * intLenSvyzArm / 1000
    'кол-во связевых верхних стержней
    intKolSvyzVerhSter = intLenRab \ intShagSvyzVerhArm + 1 'деление нацело
    intVal = intLenRab Mod intShagSvyzVerhArm
    If intVal > 25 Then intKolSvyzVerhSter = intKolSvyzVerhSter + 1
    'кол-во связевых нижних стержней
    intKolSvyzNizSter = intLenRab \ intShagSvyzNizArm + 1 'деление нацело
    intVal = intLenRab Mod intShagSvyzNizArm
    If intVal > 25 Then intKolSvyzNizSter = intKolSvyzNizSter + 1
    'масса простран.каркаса
    dMassaProsKar = intP * dMassaPlosKar + dMassaEdSvyzNizSter * intKolSvyzNizSter + dMassaEdSvyzVerhSter * intKolSvyzVerhSter
  End If
  
  'наименовыания для стержней
  sNaimVerhArm = intDiamVerhArm & "-" & sKlassVerhArm & " " & sGOSTVerhArm & " L=" & intLenProdolArm
  sNaimNizArm = intDiamNizArm & "-" & sKlassNizArm & " " & sGOSTNizArm & " L=" & intLenProdolArm
  sNaimPopArm = intDiamPopArm & "-" & sKlassPopArm & " " & sGOSTPopArm & " L=" & intLenPopArm
  sNaimSvyzVerhArm = intDiamSvyzVerhArm & "-" & sKlassSvyzVerhArm & " " & sGOSTSvyzVerhArm & " L=" & intLenSvyzArm
  sNaimSvyzNizArm = intDiamSvyzNizArm & "-" & sKlassSvyzNizArm & " " & sGOSTSvyzNizArm & " L=" & intLenSvyzArm
  
  If Err Then
    strError = Err.Description
    Err.Clear
  End If
  
End Sub
