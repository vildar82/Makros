Attribute VB_Name = "About"
Attribute VB_Base = "0{2AA02E5A-E585-48CB-AA3F-37C736A6015F}{291E9E7B-3212-48AF-96C0-631CBB670BA6}"
Attribute VB_GlobalNameSpace = False
Attribute VB_Creatable = False
Attribute VB_PredeclaredId = True
Attribute VB_Exposed = False
Attribute VB_TemplateDerived = False
Attribute VB_Customizable = False


Option Explicit

Private Sub CommandButton1_Click()
Hide
End Sub

Private Sub UserForm_QueryClose(Cancel As Integer, CloseMode As Integer)
   Hide
End Sub

Attribute VB_Name = "ClassINI"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
 
Private strInI As String
 
'// Win API Declares
Private Declare Function WritePrivateProfileString _
  Lib "kernel32" Alias "WritePrivateProfileStringA" _
 (ByVal lpApplicationName As String, _
  ByVal lpKeyName As Any, _
  ByVal lpString As Any, _
  ByVal lpFileName As String) As Long
 
Private Declare Function GetPrivateProfileString _
  Lib "kernel32" Alias "GetPrivateProfileStringA" _
 (ByVal lpApplicationName As String, _
  ByVal lpKeyName As Any, _
  ByVal lpDefault As String, _
  ByVal lpReturnedString As String, _
  ByVal nSize As Long, _
  ByVal lpFileName As String) As Long
 
Private Function MakePath(ByVal strFileName As String, _
  ByVal strPath As String) As String
 
 '// Makes an INI file: Guarantees a sub dir
 Do While Right$(strPath, 1) = "\"
   strPath = Left$(strPath, Len(strPath) - 1)
 Loop
 
 Do While Left$(strFileName, 1) = "\"
   strFileName = Mid$(strFileName, 2)
 Loop
 
 '// Return the path
 MakePath = strPath & "\" & strFileName
End Function
 
Public Sub CreateIni(strFileName As String, strPath As String)
 '// Make a new ini file
 strInI = MakePath(strFileName, strPath)
End Sub
 
Public Sub WriteFile(strSection As String, _
 strKey As String, _
 strValue As String)
 
 '// Write to strINI
 WritePrivateProfileString strSection, _
   strKey, strValue, strInI
End Sub
 
Public Function GetFile(strSection As String, _
  strKey As String) As String
 
  Dim strTmp As String
  Dim lngRet As String
 
  strTmp = String$(300, 0)
  lngRet = GetPrivateProfileString(strSection, _
    strKey, "", strTmp, _
    Len(strTmp), strInI)
 
  GetFile = StrZ(strTmp)
 
End Function
 
Public Property Let INIFile(ByVal New_IniPath As String)
   'Устанавливаем путь к файлу ini
   strInI = New_IniPath
End Property
Public Property Get INIFile() As String
   INIFile = strInI
End Property
 
 
'v_1.0.0 990630
Private Function StrZ(par As String) As String
Dim nSize As Long, i As Long, Rez As String
   nSize = Len(par)
   i = InStr(1, par, Chr(0)) - 1
   If i > nSize Then i = nSize
   If i < 0 Then i = nSize
   StrZ = Mid(par, 1, i)
End Function

Attribute VB_Name = "FormSpecRost"
Attribute VB_Base = "0{98348317-488F-4024-8134-F81F4D43D8FE}{E7969685-1954-48F2-8A98-4F72228B2E68}"
Attribute VB_GlobalNameSpace = False
Attribute VB_Creatable = False
Attribute VB_PredeclaredId = True
Attribute VB_Exposed = False
Attribute VB_TemplateDerived = False
Attribute VB_Customizable = False
Option Explicit

  'признак того что это пользователь скрыл форму
  Dim mbolHide As Boolean
  Dim mbolListBoxClick As Boolean 'для определения зацикливания операции
  
  Public poProsKarSech As clProsKarSech 'параметы простр.сечений
  
  Public oShell As New Shell32.Shell
  
Private Sub ButtonExit_Click()
  
  'предупреждение
  If MsgBox("Выход без возможности продолжения?", vbOKCancel + vbQuestion, pcsVBProjectName) = vbCancel Then
    Exit Sub
  End If
  
  'сохранение фамилии пользователя если вписана
  If FormSpecRost.TextBoxFam6 <> "" Then
    Functions.SetUserFamily FormSpecRost.TextBoxFam6
  End If
  
  End
  
End Sub

Private Sub cbShtamp1_Click()
   Functions.VerifyCheckBoxForShtamp
End Sub
Private Sub cbShtamp2_Click()
   Functions.VerifyCheckBoxForShtamp
End Sub
Private Sub cbShtamp3_Click()
   Functions.VerifyCheckBoxForShtamp
End Sub
Private Sub cbShtamp4_Click()
   Functions.VerifyCheckBoxForShtamp
End Sub
Private Sub cbShtamp5_Click()
   Functions.VerifyCheckBoxForShtamp
End Sub
Private Sub cbShtamp6_Click()
   Functions.VerifyCheckBoxForShtamp
End Sub

Private Sub CheckBoxMarkaK_Click()

End Sub

Private Sub CheckBoxShifrBS_Click()
  If Not oShifr Is Nothing Then
    If CheckBoxShifrBS.Value = True Then
      TextBoxShifr = oShifr.Shifr & oShifr.BS
    Else
      TextBoxShifr = oShifr.Shifr
    End If
  End If
End Sub

Private Sub CheckBoxSterSetky_Click()
  TextBoxDiamSterSetky.Enabled = CheckBoxSterSetky.Value
  TextBoxLSterSetky.Enabled = CheckBoxSterSetky.Value
  TextBoxKolSterSetky.Enabled = CheckBoxSterSetky.Value
  TextBoxKlassSterSetky.Enabled = CheckBoxSterSetky.Value
  TextBoxGostSterSetky.Enabled = CheckBoxSterSetky.Value
End Sub

Private Sub CheckBoxUsilenie_Change()
  'открываем/закрываем Frame усиления
  FrameUsilenie.Visible = CheckBoxUsilenie.Value
'  TextBoxUsLenSech.Enabled = CheckBoxUsilenie.Value
'  TextBoxUsShagVerhArm.Enabled = CheckBoxUsilenie.Value
'  TextBoxUsShagNizArm.Enabled = CheckBoxUsilenie.Value
'  TextBoxUsDiamVerhArm.Enabled = CheckBoxUsilenie.Value
'  TextBoxUsDiamNizArm.Enabled = CheckBoxUsilenie.Value
'  TextBoxUsKlassVerhArm.Enabled = CheckBoxUsilenie.Value
'  TextBoxUsKlassNizArm.Enabled = CheckBoxUsilenie.Value
'  TextBoxUsGOSTVerhArm.Enabled = CheckBoxUsilenie.Value
'  TextBoxUsGOSTNizArm.Enabled = CheckBoxUsilenie.Value

  'определяем кол.каркасов для усиления (по умолчанию = кол.карксов)
  Dim iKol As Integer
  iKol = Me.ListViewProsKar.SelectedItem.SubItems(1)
  TextBoxUsKolSech = iKol
  
End Sub

Private Sub cmbAddPerepad_Click()
  
  Dim oListItema As ListItem
  
  Set oListItema = ListViewPerepady.ListItems.Add(, , TextBoxHPerepada)
  oListItema.SubItems(1) = TextBoxHRostvPerepada
  oListItema.SubItems(2) = TextBoxWidthRostvPerepada
  oListItema.SubItems(3) = TextBoxKolPerepadov
  oListItema.SubItems(4) = TextBoxWidthPerepada
  oListItema.SubItems(5) = TextBoxKolRowShpilek
  oListItema.SubItems(6) = TextBoxDiamSter1Perepada
  oListItema.SubItems(7) = TextBoxKlassSter1Perepada
  oListItema.SubItems(8) = TextBoxGostSter1Perepada
  oListItema.SubItems(9) = TextBoxDiamSter2Perepada
  oListItema.SubItems(10) = TextBoxKlassSter2Perepada
  oListItema.SubItems(11) = TextBoxGostSter2Perepada
  oListItema.SubItems(12) = TextBoxDiamSter3Perepada
  oListItema.SubItems(13) = TextBoxKlassSter3Perepada
  oListItema.SubItems(14) = TextBoxGostSter3Perepada
  oListItema.SubItems(15) = TextBoxDiamSter4Perepada
  oListItema.SubItems(16) = TextBoxKlassSter4Perepada
  oListItema.SubItems(17) = TextBoxGostSter4Perepada
  
End Sub

Private Sub cmbAddSechPlosKar_Click()
  'добавить запись в листвиевер параметров плоского каркаса
  Dim oListItem As ListItem
  Dim oPlosKar As clKarkas
  Dim bolYes As Boolean
  
  'если уже есть такое сечение, то изменяем его
  For Each oListItem In ListViewPlosKarSech.ListItems
    If oListItem.Text = TextBoxNSechPlosKar Then
      bolYes = True
      Exit For
    End If
  Next
  'если нет, то добавляем новую строчку
  If bolYes = False Then
    Set oListItem = ListViewPlosKarSech.ListItems.Add(1, , TextBoxNSechPlosKar)
  End If
  
  oListItem.ListSubItems.Add 1, , TextBoxWPlosKar
  oListItem.ListSubItems.Add 2, , TextBoxnPlosKar
  oListItem.ListSubItems.Add 3, , TextBoxn1PlosKar
  oListItem.ListSubItems.Add 4, , TextBoxSPlosKar
  oListItem.ListSubItems.Add 5, , TextBoxFPlosKar
  oListItem.ListSubItems.Add 6, , TextBoxKlassSvyzPlosKar
  oListItem.ListSubItems.Add 7, , TextBoxGOSTSvyzVerhPlosKar
  oListItem.ListSubItems.Add 8, , TextBoxS1PlosKar
  oListItem.ListSubItems.Add 9, , TextBoxF1PlosKar
  oListItem.ListSubItems.Add 10, , TextBoxKlass1SvyzPlosKar
  oListItem.ListSubItems.Add 11, , TextBoxGOSTSvyzNizPlosKar
  
  'снимаем галочку и признак обраблотки
  'определяем текущий плоский каркас
  Set oPlosKar = pcolClPlosKar.Item(ListViewPlosKar.SelectedItem.Text)
  oPlosKar.bolObrabotan = False
  'снимаем галочку
  ListViewPlosKar.SelectedItem.SmallIcon = 0
  
End Sub

Private Sub cmbAttension_Click()
  
  Dim sText As String
  
  sText = "Напоминание. В спецификациях считаются:" & vbCr & vbCr & _
      "1. Каркасы - блоки с атрибутами марки, конструкции. Со след. условиями:" & vbCr & _
         "В имени блока есть буква К." & vbCr & _
         "Имя блока = марке каркаса." & vbCr & _
         "К марке каркаса (к имени блока и значению атрибута) допускаеся добавлять в скобках высоту ростверка (6)." & vbCr & _
         "Для плоских каркасов в имени блока в скобках можно указывать кол-во каркасов (шт.2)." & vbCr & _
         "Атрибут на слое " & pclOptions.psKarAtrConstrLayer & ", со значением = " & pclOptions.psKarAtrConstrText & "." & vbCr & vbCr & _
      "2. Доп.стержни - блоки с именем вида: " & pclOptions.psDopSterConst & "18L1800(шт.8)" & vbCr & _
        "где: 18 - диаметр, (шт.8) - кол-во стержней," & vbCr & _
        "L - длина стержня, мм." & vbCr & vbCr & _
      "3. Сетки - блоки с именем вида: " & pclOptions.psSetkaConst & " С1(шт.3)" & vbCr & _
        "где: С1 - марка сетки, (шт.3) - кол-во сеток."
  
  MsgBox sText, vbInformation, pcsVBProjectName
  
End Sub

Private Sub cmbCancelLoaded_Click()
  'удаление загруженных данных
  TextBoxLoadedRaschet = ""
  Set pcolLoadedProsKar = Nothing
  Set pcolLoadedPlosKar = Nothing
  Set pcolLoadedPlosKarSech = Nothing
  Set pcolLoadedDopSterg = Nothing
  Set pcolLoadedSetky = Nothing
End Sub

Private Sub cmbClearParamProsKarDef_Click()
  'очистить массивы сохраненных параметров простр каркасов
  pclOptions.ClearProsKarParamSech
End Sub

Private Sub cmbCopyKarForSpec_Click()

End Sub

Private Sub cmbDelClProsKar_Click()
  'удаление записи каркаса из расчета
  Dim oClProsKar As clKarkas
  
  If ListViewProsKar.SelectedItem Is Nothing Then
    MsgBox "Не выбрана запись", vbExclamation, pcsVBProjectName
    Exit Sub
  End If
  
  'удаление из коллекции
  pcolClProsKar.Remove (ListViewProsKar.SelectedItem.Text)
  
  'удаление из листвиевера
  ListViewProsKar.ListItems.Remove ListViewProsKar.SelectedItem.index
  
End Sub

Private Sub cmbDelPerepad_Click()
  
  If ListViewPerepady.SelectedItem Is Nothing Then Exit Sub
  
  ListViewPerepady.ListItems.Remove ListViewPerepady.SelectedItem.index
  
End Sub

'Private Sub cmbDelRaschet_Click()
'  'Удалить расчет из комбобокса расчыетов
'
'  Dim index As Integer
'
'  On Error GoTo HasError
'
'  index = ComboBoxLoadRaschet.ListIndex
'
'  If index = -1 Then
'    MsgBox "Не выбрано имя файла ростверка, расчет которого нужно удалить!", vbOKOnly + vbExclamation, pcsVBProjectName
'    Exit Sub
'  End If
'
'  Dim sFullPathRaschet As String
'
'  sFullPathRaschet = ComboBoxLoadRaschet.List(index, 2)
'
'  ComboBoxLoadRaschet.RemoveItem index
'
'  'Удалить папку со спецификациями этого расчета?
''  If MsgBox("Удалить папку со спецификациями этого расчета?", vbYesNo + vbQuestion, pcsVBProjectName) = vbYes Then
''    Dim sFolderPath As String
''    Dim fs As filesys
''    sFolderPath = GetFolderPathFromFileFullPath(sFullPathRaschet)
''    RmDir sFolderPath
''  End If
'
'  Exit Sub
'HasError:
'  Select Case Err.Number
'    Case Else
'      MsgBox Err.Description, vbCritical, pcsVBProjectName
'  End Select
'
'End Sub

Private Sub cmbDelSechPlosKar_Click()
  'удалить сечение
  Dim oPlosKar As clKarkas
  
  'проверяем выделена ли строка в листвиевере сечений
  If ListViewPlosKarSech.SelectedItem Is Nothing Then Exit Sub
  
  'удаление записи из листвиевера
  ListViewPlosKarSech.ListItems.Remove ListViewPlosKarSech.SelectedItem.index
  
  'удаление признака обработки плоского каркаса
  'получаем объект из коллекции по ключевому имени
  'определяем текущий плоский каркас
  Set oPlosKar = pcolClPlosKar.Item(ListViewPlosKar.SelectedItem.Text)
  oPlosKar.bolObrabotan = False
  
  'снимаем галочку
  ListViewPlosKar.SelectedItem.SmallIcon = 0
  
End Sub

Private Sub cmbDelSelBl_Click()
  'удалить выбранный блок из коллекции блоков выбранного типа
  
  Dim colBlCurType As Collection
  Dim oBlRef As AcadBlockReference
  Dim sType As String
  Dim index As Integer
  Dim IndexType As Integer
  
  index = ListBoxBlName.ListIndex
  If index = -1 Then
    MsgBox "Не выбрано имя блока!", vbExclamation, pcsVBProjectName
    Exit Sub
  End If
  IndexType = ListBoxObjectsType.ListIndex
  If IndexType = -1 Then
    MsgBox "Не выбран тип блоков!", vbExclamation, pcsVBProjectName
    Exit Sub
  End If
  
  'определяем коллекцию, по ListBoxObjectsType
  Select Case IndexType
    Case 0 'Каркасы
      Set colBlCurType = pcolBlKar
      sType = "Каркасов"
    Case 1 'Сетки
      Set colBlCurType = pcolBlSetky
      sType = "Сеток"
    Case 2 'Доп стержни
      Set colBlCurType = pcolBlDopSterg
      sType = "Доп.стержней"
    Case 3 'Неопределенние
      Set colBlCurType = pcolNeoprBlock
      sType = "Неопределенные"
      Exit Sub
  End Select
  
  'удаляем блок из коллекции
  colBlCurType.Remove index + 1 'в коллекциях нумерация с 1 начинается!!!, а в листбоксе с 0
  
  'удаляем блок из листбокса
  ListBoxBlName.RemoveItem index

Exit Sub
HasError:
  Select Case Err.Number
    Case -2145386420 'объект был стерт
      'удаляем блок из коллекции, из листбокса
      colBlCurType.Remove (index + 1)
      ListBoxBlName.RemoveItem index
      MsgBox "Блок был удален Вами!", vbCritical, pcsVBProjectName
    Case Else
      MsgBox Err.Description, vbCritical, pcsVBProjectName
  End Select
End Sub

Private Sub cmbExplorer_Click()
  'открыть проводник, папку со спецификациями
  
  If TextBoxFolderSpec.Text <> "" Then
    oShell.Open psFolderSpecPath
  End If
  
End Sub

Private Sub cmbFormaShablon_Click()
    
    'Вывод списка каркасов в Форму (Форма.dwg)
   'для заполнения, и повторного запуска прграммы
   
   'Если в коллекциях элементов ростверка есть блоки, то можно составлять форму
   If pcolBlKar.Count <> 0 Or pcolBlSetky.Count <> 0 Or pcolBlDopSterg.Count <> 0 Then
        'построение таблицы
        Me.Hide
        Functions.FormaForDopParam
    Else
        MsgBox ("Сначала сделайте выбор блоков на чертеже")
    End If
    
End Sub

Private Sub cmbHide_Click()
  'скрываем форму, по-идеи должна сохранится
  'кажется открытие нового чертежа выгружает форму????!!!! Нет, проверил, сохраяется!
  mbolHide = True 'означает что это именно пользователь скрыл форму
  Hide
End Sub

Private Sub cmbInsertTableHvost_Click()
  'вставка таблицы хвостов
  Dim oTable As AcadTable
  Dim vPt As Variant
  Dim aiHvost(9) As Integer
  Dim i As Integer
  
  On Error GoTo HasError
  
  Me.Hide
  
  'создаем табличный стиль
  MakeTableStyleForSpec
  
  vPt = ThisDrawing.Utility.GetPoint(, "Точка вставки таблицы")
  Set oTable = ThisDrawing.ModelSpace.AddTable(vPt, 12, 3, 8, 25)
  
  oTable.StyleName = "Спецификация"
  
  oTable.SetCellValue 0, 0, "Хвосты каркасов"
  oTable.SetCellValue 1, 0, "Номер"
  oTable.SetCellValue 1, 1, "Длина"
  oTable.SetCellValue 1, 2, "Диаметр"
  
  aiHvost(0) = TextBoxHvost0
  aiHvost(1) = TextBoxHvost1
  aiHvost(2) = TextBoxHvost2
  aiHvost(3) = TextBoxHvost3
  aiHvost(4) = TextBoxHvost4
  aiHvost(5) = TextBoxHvost5
  aiHvost(6) = TextBoxHvost6
  aiHvost(7) = TextBoxHvost7
  aiHvost(8) = TextBoxHvost8
  aiHvost(9) = TextBoxHvost9
  
  For i = 0 To 9
    oTable.SetCellValue i + 2, 0, i
    oTable.SetCellValue i + 2, 1, aiHvost(i)
  Next
  
  oTable.ScaleEntity vPt, 50
  
  Me.Show
  
Exit Sub
HasError:
  MsgBox Err.Description, vbCritical, pcsVBProjectName
End Sub

Private Sub cmbInsertVedStaly_Click()
  'вставляем блок
  Dim oBlRef As AcadBlockReference
  Dim selSet As AcadSelectionSet
  Dim oEnt As AcadEntity
  Dim intCmdEcho As Integer
  Dim strCommand As String
  Dim aiCode(0) As Integer
  Dim avDate(0) As Variant
  
  If psBlVedStaly = "" Then Exit Sub
  
  Me.Hide
  
  pdocSpecRost.Activate
  
  intCmdEcho = ThisDrawing.GetVariable("cmdecho")
  ThisDrawing.SetVariable "cmdecho", 0
   
   'вставка блока
   strCommand = "(command " & _
                   Chr(34) & "._-insert" & Chr(34) & " " & _
                   Chr(34) & psBlVedStaly & Chr(34) & " " & _
                   Chr(34) & "_X" & Chr(34) & " " & 100 & " " & Chr(34) & "_Y" & Chr(34) & " " & 100 & " " & _
                   "pause 0)(princ)"
                   
   ThisDrawing.SendCommand strCommand & vbCr
   'ThisDrawing.SendCommand "_zoom" & vbCr & "a" & vbCr

   ThisDrawing.SetVariable "cmdecho", intCmdEcho
     
  Me.Show
  
End Sub

Private Sub cmbLoadRaschet_Click()
  'загрузка расчета из txt файла

'  Dim oExplorer As New Shell
  
'  'проверка сделан ли выбор блоков
'  If pcolBlKar.Count = 0 And pcolBlSetky.Count = 0 And pcolBlDopSterg.Count = 0 Then
'    MsgBox "Нужно сделать выбор блоков на чертеже. Нажмите кнопку Выбор.", vbCritical, pcsVBProjectName
'    Exit Sub
'  End If
  
  'проверить существование заданного файла в текстбоксе
  If TextBoxLoadedRaschet.Text = "" Then
      MsgBox "Не задан текстовый файл данных расчета", vbExclamation, pcsVBProjectName
      Exit Sub
  End If
  
  Dim sval As String
  sval = Dir(TextBoxLoadedRaschet.Text)
  If sval = "" Then
      MsgBox "Файл не найден!", vbCritical, pcsVBProjectName
      Exit Sub
  End If
  
  On Error GoTo HasError
  
  Functions.LoadRaschet TextBoxLoadedRaschet.Text
  'если уже были выбраны блоки, то применяем загруженные объекты к ним
  If pcolClProsKar.Count <> 0 Or pcolClPlosKar.Count <> 0 Or pcolClDopStergny.Count <> 0 Or pcolClSetky.Count <> 0 Then
    Functions.PrimLoadedObjects
  End If
  
  'сплэш успешной загрузки данных
  MsgBox "Данные загружены", vbInformation, pcsVBProjectName
  
  Exit Sub
  
HasError:
  MsgBox Err.Description, vbCritical, pcsVBProjectName
  
End Sub

'Private Sub cmbLoadRaschet2_Click()
'
'  Dim index As Integer
'
'  index = ComboBoxLoadRaschet.ListIndex
'
'  If index = -1 Then
'    MsgBox "Не выбрано имя файла ростверка, расчет которого нужно загрузить!", vbOKOnly + vbExclamation, pcsVBProjectName
'    Exit Sub
'  End If
'
'  Dim sTxtFileFullPath As String
'
'  sTxtFileFullPath = ComboBoxLoadRaschet.List(index, 2)
'
'  Functions.LoadRaschet sTxtFileFullPath
'  'если уже были выбраны блоки, то применяем загруженные объекты к ним
'  If pcolClProsKar.Count <> 0 Or pcolClPlosKar.Count <> 0 Or pcolClDopStergny.Count <> 0 Or pcolClSetky.Count <> 0 Then
'    Functions.PrimLoadedObjects
'  End If
'
'  'записываем папку и имя загруженного расчета
'  'TextBoxLoadedRaschet = sTxtFileFullPath
'
'End Sub

Private Sub cmbNextProsKar_Click()
  'сохранить текущие параметры для неизвестных сечений (По умолчанию)
  pclOptions.SaveProsKarParamSech "0"
End Sub

Private Sub cmbOpenPlosKar_Click()
  'открыть чертеж плоских каркасов
  
  On Error GoTo HasError
  
  If TextBoxFilePlosPath.Text <> "" Then
    Documents.Open psFilePlosPath
  End If

Exit Sub
HasError:
  TextBoxFilePlosPath = ""
End Sub

Private Sub cmbOpenProsKar_Click()
  'открыть чертеж простр. каркасов
  On Error GoTo HasError
  
  If TextBoxFileProsPath.Text <> "" Then
    Documents.Open psFileProsPath
  End If
Exit Sub
HasError:
  TextBoxFileProsPath = ""
End Sub

Private Sub cmbOpenSoderg_Click()
  'открыть чертеж простр. каркасов
  On Error GoTo HasError
  
  If TextBoxFileSodergPath.Text <> "" Then
    Documents.Open psFileSodergPath
  End If
Exit Sub
HasError:
  TextBoxFileSodergPath = ""
End Sub

Private Sub cmbOpenTitul_Click()
  'открыть чертеж обложек
  On Error GoTo HasError
  
  If TextBoxFileTitPath.Text <> "" Then
    Documents.Open psFileTitPath
  End If

Exit Sub
HasError:
  TextBoxFileTitPath = ""
End Sub

Private Sub cmbInsertSpec_Click()
  
  'вставляем блок
  Dim oBlRef As AcadBlockReference
  Dim selSet As AcadSelectionSet
  Dim oEnt As AcadEntity
  Dim intCmdEcho As Integer
  Dim strCommand As String
  Dim aiCode(0) As Integer
  Dim avDate(0) As Variant
  
  If psBlSpecElem = "" Then Exit Sub
  
  Me.Hide
  
  pdocSpecRost.Activate
  
  intCmdEcho = ThisDrawing.GetVariable("cmdecho")
  ThisDrawing.SetVariable "cmdecho", 0
   
   'вставка блока
   strCommand = "(command " & _
                   Chr(34) & "._-insert" & Chr(34) & " " & _
                   Chr(34) & psBlSpecElem & Chr(34) & " " & _
                   Chr(34) & "_X" & Chr(34) & " " & 100 & " " & Chr(34) & "_Y" & Chr(34) & " " & 100 & " " & _
                   "pause 0)(princ)"
                   
   ThisDrawing.SendCommand strCommand & vbCr
   'ThisDrawing.SendCommand "_zoom" & vbCr & "a" & vbCr

   ThisDrawing.SetVariable "cmdecho", intCmdEcho
   
'  'находим этот блок и разбиваем его
'  Set selSet = Functions.GetSelSet("Спецификация")
'  aiCode(0) = 0: avDate(0) = "insert"
' ' aiCode(1) = 2: avDate(1) = psBlSpecElem
'  selSet.Select acSelectionSetAll, , , aiCode, avDate
'  For Each oBlRef In selSet
'    oBlRef.Explode
'    oBlRef.Delete
'  Next
  
  Me.Show
  
End Sub

Private Sub cmbPrimDopSter_Click()
  'сохраняем номер позиции для доп стержня
  
  'проверяем выбран ли доп стержень
  If ListViewDopSter.SelectedItem Is Nothing Then
    MsgBox "Нужно выбрать стержень в списке."
    Exit Sub
  End If
  
  If TextBoxDopSterPoz = "" Then
    MsgBox "Позиция не назначена.", vbCritical, pcsVBProjectName
    Exit Sub
  End If
  
  Dim oDopSterItem As clDopStergen
  Dim oDopSter As clDopStergen
  Dim aiPoz() As Integer
  Dim i As Integer
  
  ReDim aiPoz(pcolClDopStergny.Count - 1)
  
  'находим выделенный в листвиевере стержень в коллекции
  For Each oDopSterItem In pcolClDopStergny
    If oDopSterItem.sNaimenovanie = ListViewDopSter.SelectedItem.Text Then
      Set oDopSter = oDopSterItem
    End If
    aiPoz(i) = oDopSterItem.iPoz
    i = i + 1
  Next
  
  'проверяем позицию
  For i = 0 To UBound(aiPoz)
    If Val(TextBoxDopSterPoz) = aiPoz(i) Then
      MsgBox "Такая позиция уже есть", vbExclamation, pcsVBProjectName
      Exit Sub
    End If
  Next
  
  oDopSter.iPoz = Val(TextBoxDopSterPoz)
  oDopSter.bolObrabotan = True
  
  'ставим галочку
  ListViewDopSter.SelectedItem.SmallIcon = 1
  
End Sub

Private Sub cmbPrimPerepady_Click()
  'применить перепады
  
  'ставим галки всем записям перепадам
  
  'признак обработки перепадов
  pbolObrabPerepadov = True
  
End Sub

Private Sub cmbPrimProsKar_Click()
'сохранение параметров с полей в выбранный каркас
  If ListViewProsKar.SelectedItem Is Nothing Then
    MsgBox "Не выбран каркас!", vbExclamation, pcsVBProjectName
    Exit Sub
  End If
  
  Dim oClProsKar As clKarkas
  Dim sKarClickName As String
  'применяем значения с формы в поля объекта каркаса
  sKarClickName = ListViewProsKar.SelectedItem.Text
  Set oClProsKar = pcolClProsKar.Item(sKarClickName)
  'сохраняем параметры сечения в объекте каркаса
  Functions.SetParamProsKar oClProsKar
  
  'шаг.доп.поп.стер
  If oClProsKar.bolD = True Then
    oClProsKar.intShagDopPopSter = FormSpecRost.TextBoxShagDopPopSter
  End If
  
  'сохраняем параметры сечения в применяемые сечения
  '**** изменения 12.11.09 сохранять параметры сечения только для панелек (для кирпичек не нужно)
  'If FormSpecRost.CheckBoxMarkaK.Value = False Then
      poProsKarSech.SetParamSech
  'End If
  
  'галочки для выделенного элемента списка листвиевера
  ListViewProsKar.SelectedItem.SmallIcon = 1
  'сечение
  ListViewProsKar.SelectedItem.SubItems(2) = oClProsKar.sNSech
  
  'нужно проверить есть ли обработанные каркасы с этим сечением
  'если есть прменить к ним изменения
  Dim bolYes As Boolean
  For Each oClProsKar In pcolClProsKar
    If oClProsKar.bolObrabotan = True Then
      If oClProsKar.sNSech = TextBoxNSech Then
        If oClProsKar.strFirstName <> sKarClickName Then
          Functions.SetParamProsKar oClProsKar
          bolYes = True
        End If
      End If
    End If
  Next
  
'  If bolYes = True Then
'    MsgBox "Параметры были применены для всех каркасов этого сечения", vbInformation, pcsVBProjectName
'  End If
  
End Sub

Private Sub cmbPrimPlosKar_Click()
  'применить параметры плоского каркаса в класс каркасов clKarkas
  'и заполнить параметры сечений в класс параметров плоских каркасов
  Dim iCountSech As Integer
  Dim sNameSelPlosKar As String
  Dim oPlosKarSech As clPlosKarSech
  Dim oPlosKar As clKarkas
  Dim i As Integer
  Dim oListItem As ListItem
  Dim oSelectedListItem As ListItem
  Dim iKolKarPoSech As Integer 'распределенное кол-во плоскар по сечениям
  
  If ListViewPlosKar.SelectedItem Is Nothing Then Exit Sub
  
  'определяем текущий плоский каркас
  sNameSelPlosKar = ListViewPlosKar.SelectedItem.Text
  Set oPlosKar = pcolClPlosKar.Item(sNameSelPlosKar)
  
  'проверяем все ли каркасы распределены по сечениям
  iCountSech = ListViewPlosKarSech.ListItems.Count
  If iCountSech = 0 Then
    MsgBox "Задайте параметры сечения в которое входит этот плоский каркас и добавьте его в список сечений.", vbExclamation, pcsVBProjectName
    Exit Sub
  End If
  For Each oListItem In ListViewPlosKarSech.ListItems
    iKolKarPoSech = iKolKarPoSech + oListItem.ListSubItems(2) * oListItem.ListSubItems(3)
  Next
  If iKolKarPoSech < oPlosKar.intKolKar Then
    MsgBox "Не все каркасы распределены по сечениям", vbCritical, pcsVBProjectName
    Exit Sub
  ElseIf iKolKarPoSech > oPlosKar.intKolKar Then
    MsgBox "Кол-во каркасов распределенных по сечениям превышает общее кол-во каркасов", vbCritical, pcsVBProjectName
    Exit Sub
  End If
  
  'сохраняем параметры каркаса в объект каркаса из коллекции плоских каркасов
  oPlosKar.intHeightRost = TextBoxHPlosKar
  oPlosKar.intCenterVerhArm = TextBoxZachVerhPlosKar
  oPlosKar.intCenterNizArm = TextBoxZachNizPlosKar
  oPlosKar.sKlassVerhArm = TextBoxKlassVerhPlosKar
  oPlosKar.sKlassNizArm = TextBoxKlassNizPlosKar
  oPlosKar.sKlassPopArm = TextBoxKlassPopPlosKar
  oPlosKar.sGOSTVerhArm = TextBoxGOSTVerhPlosKar
  oPlosKar.sGOSTNizArm = TextBoxGOSTNizPlosKar
  oPlosKar.sGOSTPopArm = TextBoxGOSTPopPlosKar
  'если есть "д"
  If oPlosKar.bolD = True Then
    oPlosKar.intShagDopPopSter = TextBoxShagDopPopPlosKar
  End If
  
  'признак обработки каркаса
  oPlosKar.bolObrabotan = True
  
  'находим объект сечения в колекции плоск.каркасов(парам.сеч.)
  Set oPlosKarSech = pcolClPlosKarSech.Item(sNameSelPlosKar)
  'сохраняем параметры сечений
  oPlosKarSech.SetParamSech (oPlosKar.intLenRab)
  oPlosKarSech.piKolKar = oPlosKar.intKolKar
  
  'ставим галочку
  ListViewPlosKar.SelectedItem.SmallIcon = 1
  
End Sub

Private Sub cmbPrimSetky_Click()
  'записываем параметры в сетку
  
  'проверяем выбрана ли сетка
  If ListViewSetky.SelectedItem Is Nothing Then
    MsgBox "Не выбрана сетка", vbExclamation, pcsVBProjectName
    Exit Sub
  End If
  
  Dim oSetka As clSetky
  Dim oSetkaTemp As clSetky
  Dim bolYes As Boolean
  
  'находим сетку
  Set oSetka = pcolClSetky.Item(ListViewSetky.SelectedItem.Text)
  If CheckBoxSterSetky.Value = True Then
      oSetka.pbDopSter = True
      oSetka.piDiamDopSter = TextBoxDiamSterSetky
      oSetka.piLenDopSter = TextBoxLSterSetky
      oSetka.piKolDopSter = TextBoxKolSterSetky
      oSetka.psKlassDopSter = TextBoxKlassSterSetky
      oSetka.psGOSTDopSter = TextBoxGostSterSetky
  End If
    oSetka.piDiamVertSter = TextBoxDiam1Setky
    oSetka.piShagVertSter = TextBoxShag1Setky
    oSetka.piKolShagovVertik = TextBoxN1Setky
    oSetka.psKlassVertSter = TextBoxKlass1Setky
    oSetka.psGOSTVertSter = TextBoxGost1Setky
    oSetka.piDiamHorSter = TextBoxDiam2Setky
    oSetka.piShagHorSter = TextBoxShag2Setky
    oSetka.piKolShagovHoris = TextBoxN2Setky
    oSetka.psKlassHorSter = TextBoxKlass2Setky
    oSetka.psGOSTHorSter = TextBoxGost2Setky
    
    'если есть сетки с такоцйже маркой
    For Each oSetkaTemp In pcolClSetky
      If oSetkaTemp.psMarka = oSetka.psMarka And Not oSetkaTemp Is oSetka _
        And oSetkaTemp.pbObrab = True Then
        oSetkaTemp.piDiamVertSter = TextBoxDiam1Setky
        oSetkaTemp.piShagVertSter = TextBoxShag1Setky
        oSetkaTemp.piKolShagovVertik = TextBoxN1Setky
        oSetkaTemp.psKlassVertSter = TextBoxKlass1Setky
        oSetkaTemp.psGOSTVertSter = TextBoxGost1Setky
        oSetkaTemp.piDiamHorSter = TextBoxDiam2Setky
        oSetkaTemp.piShagHorSter = TextBoxShag2Setky
        oSetkaTemp.piKolShagovHoris = TextBoxN2Setky
        oSetkaTemp.psKlassHorSter = TextBoxKlass2Setky
        oSetkaTemp.psGOSTHorSter = TextBoxGost2Setky
        bolYes = True
      End If
    Next
  If bolYes = True Then
    MsgBox "Параметры применились для всех сеток этой марки.", vbInformation, pcsVBProjectName
  End If
  
  'ставим галку
  ListViewSetky.SelectedItem.SmallIcon = 1
  oSetka.pbObrab = True
  
End Sub

Private Sub cmbPrimToAllProsKar_Click()
  'применить параметры ко всем каркасам в листвиевере
  Dim oClProsKar As clKarkas
  Dim sKarClickName As String
  Dim oListItem As ListItem
  Dim bolYes As Boolean
  
  For Each oClProsKar In pcolClProsKar
    'если он есть в листвиевере сохранием параметры
    For Each oListItem In ListViewProsKar.ListItems
      If oListItem.Text = oClProsKar.strFirstName Then
        Functions.SetParamProsKar oClProsKar
'        'шаг.доп.поп.стер
'        If oClProsKar.bolD = True Then
'          oClProsKar.intShagDopPopSter = TextBoxShagDopPopSter 'pclOptions.piShagDopPopSterDef
'        End If
        'галочка
        oListItem.SmallIcon = 1
        'сечение
        oListItem.SubItems(2) = oClProsKar.sNSech
        bolYes = True
      End If
    Next
    If bolYes = False Then
      'если нет в листвеевере, то проверяем номер сечения если такой же то сохраняем параметры
      If TextBoxNSech = oClProsKar.sNSech Then
        'сохраняем параметры
        Functions.SetParamProsKar oClProsKar
'        'шаг.доп.поп.стер
'        If oClProsKar.bolD = True Then
'          oClProsKar.intShagDopPopSter = pclOptions.piShagDopPopSterDef
'        End If
      End If
    End If
  Next 'oClProsKar In pcolClProsKar
  
  'сохраняем параметры сечения в применяемые сечения
  poProsKarSech.SetParamSech
  
End Sub

Private Sub cmbRisPerepada_Click()
  FormRisPerepada.Show
End Sub

Private Sub cmbSaveDef_Click()
  'сохранение настроек
  pclOptions.SaveOptions
  pclOptions.SaveOptionsToIni
End Sub

Private Sub cmbSaveParamNSechPlosKarDef_Click()
  'сохранение параметров для номерав сечения плоских каркасов
  pclOptions.SavePlosKarParamSech
  pclOptions.SaveOptionsToIni
End Sub

Private Sub cmbSaveParamProsKarDef_Click()
  pclOptions.SaveProsKarParamSech Me.TextBoxNSech
  pclOptions.SaveOptionsToIni
End Sub

Private Sub cmbSavePerepStergs_Click()
  pclOptions.piDiamSter1Perepada = TextBoxDiamSter1Perepada
  pclOptions.piDiamSter2Perepada = TextBoxDiamSter2Perepada
  pclOptions.piDiamSter3Perepada = TextBoxDiamSter3Perepada
  pclOptions.piDiamSter4Perepada = TextBoxDiamSter4Perepada
  pclOptions.psKlassSter1Perepada = TextBoxKlassSter1Perepada
  pclOptions.psKlassSter2Perepada = TextBoxKlassSter2Perepada
  pclOptions.psKlassSter3Perepada = TextBoxKlassSter3Perepada
  pclOptions.psKlassSter4Perepada = TextBoxKlassSter4Perepada
  pclOptions.psGostSter1Perepada = TextBoxGostSter1Perepada
  pclOptions.psGostSter2Perepada = TextBoxGostSter2Perepada
  pclOptions.psGostSter3Perepada = TextBoxGostSter3Perepada
  pclOptions.psGostSter4Perepada = TextBoxGostSter4Perepada
  pclOptions.SaveOptionsToIni
End Sub

Private Sub cmbSelect_Click()
  'выбор блоков чертежа для расчета спец-ий
  'все расчеты выполнять заново
  
  Dim selSet As AcadSelectionSet
  Dim intCode(0) As Integer
  Dim varDate(0) As Variant
  
  Me.Hide 'скрываем форму
  
  'очищаем листбоксы
  ListBoxBlName.Clear
  ListBoxObjectsType.Clear
  
  'запоминаем текущий чертеж
  Set pdocSpecRost = ActiveDocument
  
  'очищаем пути к файлам результатов расчетов
  TextBoxFolderSpec = ""
  TextBoxFileProsPath = ""
  TextBoxFilePlosPath = ""
  TextBoxFileSodergPath = ""
  TextBoxFileTitPath = ""
  'Скрываем кнопки резукльтатов расчета
  cmbExplorer.Enabled = False
  cmbOpenPlosKar.Enabled = False
  cmbOpenProsKar.Enabled = False
  cmbOpenSoderg.Enabled = False
  cmbOpenTitul.Enabled = False
  cmbInsertSpec.Enabled = False
  cmbInsertVedStaly.Enabled = False
  cmbViewKarForSech.Enabled = False
  
  'проверка чертежа на наличие блоков на замороженных слоях
  Functions.ProvBlInFreezeLayer
  'если есть блоки на заморож слоях
  'и если нажали остановку, выходим
  If FormaFreezeBlock.cmbStop.Caption = "Закрыть" Then
    mbolHide = True 'этоже польз. остановил прогу
    Exit Sub
  End If
  
  'фильтр блоков (правда вместе с хрефами и мн-блоками!!!)
  intCode(0) = 0: varDate(0) = "insert"
  
  Set selSet = Functions.GetSelSet(pcsVBProjectName)
  'выбор на экране
  selSet.SelectOnScreen intCode, varDate
  
  If selSet.Count = 0 Then
    Me.Show
    Exit Sub
  End If
  
  'записываем заголовок для формы
  'т.е. чертеж для котрого выполняется расчет спецификаций
  Me.Caption = pcsVBProjectName & " - " & ThisDrawing.FullName
  
  'выставляем в False значения для обработки вкладок
  pbolObrabPerepadov = False
  pbolObrabPlosKar = False
  pbolObrabProsKar = False
  pbolObrabSetok = False
  pbolObraDopSter = False
  
  'проверка набора блоков в selSet на дублирование,
  'если есть дубликаты, показать форму-отчет
  Functions.ProvDublicatov
  'если есть дубл блоки
  'и если нажали остановку, выходим
  If FormaProverky.cmbStop.Caption = "Закрыть" Then
    mbolHide = True 'этоже польз. остановил прогу
    Exit Sub
  End If
  
  'определение объектов специф-ий из набора блоков
  Functions.ObrabotkaSelSet
  
  '!!!изменение. предварительная обработка вкладок, которая раньше делалась при переключении на вкладку MultiPageMain_Change().
  'обработка исходных данных проекта
  'считываем шифр с чертежа
  Functions.ObrabAttributov
  'процедура обработки блоков пространственных каркасов из коллеции выбранных блоков каркасов
  Functions.ObrabProsKar
  Functions.ObrabPlosKar
  Functions.ObrabSetok
  Functions.ObrabDopSter
  Functions.ObrabPerepadov
  
  Me.Show
  
End Sub

Private Sub cmbSelectTableHvost_Click()
  'выбрать таблицу значения хвостов и заполнить текстбоксы
  Dim oTable As AcadTable
  Dim obj As AcadObject
  Dim vPt As Variant
  
  On Error GoTo HasError
  
  Me.Hide
  
  ThisDrawing.Utility.GetEntity obj, vPt, "Выберете таблицу с длинами хвостов каркасов"
  
  If Not TypeOf obj Is AcadTable Then
    MsgBox "Это не таблица", vbCritical, pcsVBProjectName
    Exit Sub
  End If
  
  Set oTable = obj
  
  TextBoxHvost0 = oTable.GetCellValue(2, 1)
  TextBoxHvost1 = oTable.GetCellValue(3, 1)
  TextBoxHvost2 = oTable.GetCellValue(4, 1)
  TextBoxHvost3 = oTable.GetCellValue(5, 1)
  TextBoxHvost4 = oTable.GetCellValue(6, 1)
  TextBoxHvost5 = oTable.GetCellValue(7, 1)
  TextBoxHvost6 = oTable.GetCellValue(8, 1)
  TextBoxHvost7 = oTable.GetCellValue(9, 1)
  TextBoxHvost8 = oTable.GetCellValue(10, 1)
  TextBoxHvost9 = oTable.GetCellValue(11, 1)
  
  Me.Show

Exit Sub
HasError:
  MsgBox Err.Description, vbCritical, pcsVBProjectName
  
End Sub

Private Sub cmbStartSpec_Click()
  
  Dim bolYes As Boolean
  Dim oKar As clKarkas
  Dim oPlosKar As clKarkas
  
  'расчет и построение спецификаций арматурных изделий ростверка
  
  'Me.Hide
  
  If TextBoxError <> "ok" Then
    MsgBox "Не все замечания исправлены!", vbCritical, pcsVBProjectName
    Exit Sub
  End If
  
  '1. Расчет масс каркасов
  bolYes = Functions.RaschetMassKar
  If bolYes = False Then
    GoTo Rasch_Error
  End If
  
  '2. Составление колекции плоских каркасов из простран и из плоских
    'для плоских каркасов расчет массы
  On Error Resume Next
  Set pcolAllPlosKar = Nothing
  For Each oKar In pcolClProsKar
    Set oPlosKar = pcolAllPlosKar.Item(oKar.strPlosKarName)
    If Err Then
      'нет такого каркаса
      Err.Clear
      'добавляем в коллекцию плоских каркасов
      pcolAllPlosKar.Add oKar, oKar.strPlosKarName
    End If
  Next
  For Each oKar In pcolClPlosKar
    Set oPlosKar = pcolAllPlosKar.Item(oKar.strPlosKarName)
    If Err Then
      'нет такого каркаса
      Err.Clear
      'добавляем в коллекцию плоских каркасов
      pcolAllPlosKar.Add oKar, oKar.strPlosKarName
    End If
  Next
  On Error GoTo 0
  
  'проверка порядковых номеров маркиК
  If CheckBoxMarkaK.Value = True Then
    Dim sError As String
    sError = Functions.ProvMarokKInColKar(pcolAllPlosKar)
    If sError <> "" Then
      MsgBox sError, vbCritical, pcsVBProjectName
      TextBoxError = sError
      Exit Sub
    End If
  End If
  
  'сортировка пос.кар по кол-ву N
  If CheckBoxMarkaK.Value = True Then
    SortyrColPlosKarByK pcolAllPlosKar
  Else
    SortyrColPlosKarByVal pcolAllPlosKar
  End If
  
  '3.Расчет сеток
  bolYes = Functions.RaschetSetok
  If bolYes = False Then
    GoTo Rasch_Error
  End If
  
  '4.Расчет доп.стержней
  bolYes = Functions.RaschetDopSter
  If bolYes = False Then
    GoTo Rasch_Error
  End If
  
  '5.Расчет перепадов
  bolYes = Functions.RaschetPerepadov
  If bolYes = False Then
    GoTo Rasch_Error
  End If
  
  'определяем шифр
  psShifr = TextBoxShifr & ".И-Р" & TextBoxNpart
  
  'создаем коллекцию содержания
  Set pcolSoderg = New Collection
  
  '6.Создание и заполнение чертежей
  'на данный момент все должно быть известно нужно только создать и заполнить чертежи
  Functions.MakeDocumentation
  
  'Me.Show
  
Exit Sub
Rasch_Error:
  MsgBox "Найдены ошибки при расчете. Подробнее смотрите в замечаниях.", vbCritical, pcsVBProjectName
  'Me.Show
End Sub

Private Sub cmbStrePerepDef_Click()
  'выставляем значения стержней перепада по умолчанию
  TextBoxDiamSter1Perepada = pclOptions.piDiamSter1Perepada
  TextBoxDiamSter2Perepada = pclOptions.piDiamSter2Perepada
  TextBoxDiamSter3Perepada = pclOptions.piDiamSter3Perepada
  TextBoxDiamSter4Perepada = pclOptions.piDiamSter4Perepada
  TextBoxKlassSter1Perepada = pclOptions.psKlassSter1Perepada
  TextBoxKlassSter2Perepada = pclOptions.psKlassSter2Perepada
  TextBoxKlassSter3Perepada = pclOptions.psKlassSter3Perepada
  TextBoxKlassSter4Perepada = pclOptions.psKlassSter4Perepada
  TextBoxGostSter1Perepada = pclOptions.psGostSter1Perepada
  TextBoxGostSter2Perepada = pclOptions.psGostSter2Perepada
  TextBoxGostSter3Perepada = pclOptions.psGostSter3Perepada
  TextBoxGostSter4Perepada = pclOptions.psGostSter4Perepada
End Sub

Private Sub cmbView_Click()
  'показать неопр блок
  'в чертеже для спецификаций pdocSpecRost
  
  Dim oBlRef As AcadBlockReference
  Dim colBlCurType As Collection
  Dim index As Integer
  Dim IndexType As Integer
  Dim sType As String
  Dim vMin As Variant
  Dim vMax As Variant
  
  On Error GoTo HasError
  
  pdocSpecRost.Activate
  
  index = ListBoxBlName.ListIndex
  If index = -1 Then
    MsgBox "Не выбрано имя блока!", vbExclamation, pcsVBProjectName
    Exit Sub
  End If
  IndexType = ListBoxObjectsType.ListIndex
  If IndexType = -1 Then
    MsgBox "Не выбран тип блоков!", vbExclamation, pcsVBProjectName
    Exit Sub
  End If
  
  'определяем коллекцию, по ListBoxObjectsType
  Select Case IndexType
    Case 0 'Каркасы
      Set colBlCurType = pcolBlKar
      sType = "Каркасов"
    Case 1 'Сетки
      Set colBlCurType = pcolBlSetky
      sType = "Сеток"
    Case 2 'Доп стержни
      Set colBlCurType = pcolBlDopSterg
      sType = "Доп.стержней"
    Case 3 'Неопределенние
      Set colBlCurType = pcolNeoprBlock
      sType = "Неопределенные"
  End Select
  
  'находим блок в коллекции
  Set oBlRef = colBlCurType.Item(index + 1) 'в коллекциях нумерация с 1 начинается!!!, а в листбоксе с 0
  
  oBlRef.Highlight True
  
  oBlRef.GetBoundingBox vMin, vMax
  ZoomWindow vMin, vMax

Exit Sub
HasError:
  Select Case Err.Number
    Case -2145386420 'объект был стерт
      'удаляем блок из коллекции, из листбокса
      colBlCurType.Remove (index + 1)
      ListBoxBlName.RemoveItem index
      MsgBox "Блок был удален Вами!", vbCritical, pcsVBProjectName
    Case Else
      MsgBox Err.Description, vbCritical, pcsVBProjectName
  End Select
End Sub

Private Sub cmbViewKarForSech_Click()
    'Вывести список имен плоских каркасов для введенного номера сечения
    
    Dim oKar As clKarkas
    Dim sKarNameForSech As String
    
    'iNSechForView = CInt(TextBoxNSechForViewPlosKar)
    
    For Each oKar In pcolClProsKar
        If oKar.sNSech <> "" Then
            'Сверяем номера сечений
            If TextBoxNSechForViewPlosKar = oKar.sNSech Then
                If CheckBoxMarkaK.Value = True Then
                  sKarNameForSech = sKarNameForSech + oKar.strMarkaKPlos & "; "
                Else
                  sKarNameForSech = sKarNameForSech + oKar.strPlosKarName & "; "
                End If
            End If
        End If
    Next
    
    If Len(sKarNameForSech) = 0 Then
        MsgBox "Нет каркасов для сечения " & TextBoxNSechForViewPlosKar, vbInformation, pcsVBProjectName
        Exit Sub
    End If
    
    TextBoxKarForSechViewer = sKarNameForSech
    
End Sub

Private Sub cmbViewSechPlosKar_Click()
  FormRisSech.Show
End Sub

Private Sub cmdBrowse_Click()
  Dim sTxtFileFullPath As String
  
   'выбор текстового файла ("Чертёж", "*.dwg", "c:\")
  sTxtFileFullPath = OpenFile("Выбор текстового файла данных расчета", "*.txt", ThisDrawing.FullName)
  
  If sTxtFileFullPath <> "" Then
      TextBoxLoadedRaschet.Text = sTxtFileFullPath
  End If
   
End Sub

Private Sub ComboBoxFilterProsKar_Change()
  'фильтр простр.каркасов по кол-ву плоских каркасов
  Dim intKolPValue As Integer
  Dim oProsKar As clKarkas
  
  intKolPValue = Val(ComboBoxFilterProsKar.Value)
  
  ZapListViewProsKar intKolPValue, ComboBoxFilterProsKar
  
End Sub




Private Sub ListBoxObjectsType_Click()
  'выводим список блоков из соответствующей коллекции
  
  Dim colBlCurType As Collection
  Dim oBlRef As AcadBlockReference
  Dim index As Integer
  Dim sType As String
  
  If mbolListBoxClick = True Then
    mbolListBoxClick = False
    Exit Sub
  End If
  
  index = ListBoxObjectsType.ListIndex
  If index = -1 Then
    MsgBox "Не выбран тип блоков!", vbExclamation, pcsVBProjectName
    Exit Sub
  End If
  
  'определяем коллекцию, по ListBoxObjectsType
  Select Case index
    Case 0 'Каркасы
      Set colBlCurType = pcolBlKar
      sType = "Каркасов"
    Case 1 'Сетки
      Set colBlCurType = pcolBlSetky
      sType = "Сеток"
    Case 2 'Доп стержни
      Set colBlCurType = pcolBlDopSterg
      sType = "Доп.стержней"
    Case 3 'Неопределенние
      Set colBlCurType = pcolNeoprBlock
      sType = "Неопределенные"
  End Select
  
  On Error Resume Next
  
  Dim intCount As Integer
  Dim intDeletedBl As Integer
  ListBoxBlName.Clear
  intCount = 1
  For Each oBlRef In colBlCurType
    ListBoxBlName.AddItem oBlRef.Name
    If Err Then
      'блок был удален
      colBlCurType.Remove intCount
      intCount = intCount - 1
      intDeletedBl = intDeletedBl + 1
      Err.Clear
    End If
    intCount = intCount + 1
  Next
  
  On Error GoTo 0
  
    Dim intKolSelBl As Integer
    intKolSelBl = Val(Mid(LabelSelSetCount, 23))
    LabelSelSetCount = "Всего выбрано блоков: " & intKolSelBl - intDeletedBl
    'изменяем строку кол-ва типов блоков
    'выполняется процедура ListBoxObjectsType_Click
    mbolListBoxClick = True 'чтобы не повторялась эта операция
    ListBoxObjectsType.List(index) = sType & " = " & colBlCurType.Count
    
Exit Sub
'HasError:
'  Select Case Err.Number
'    Case -2145386420 'объект был стерт
'      'удаляем блок из коллекции, из листбокса
'      colBlCurType.Remove intCount
'      'изменяем запись общего кол-ва выбраных боков
'      Dim intKolSelBl As Integer
'      intKolSelBl = Val(Mid(LabelSelSetCount, 23))
'      LabelSelSetCount = "Всего выбрано блоков: " & intKolSelBl - 1
'      'изменяем строку кол-ва типов блоков
'      'выполняется процедура ListBoxObjectsType_Click
'      ListBoxObjectsType.List(index) = sType & " = " & colBlCurType.Count
'    Case Else
'      MsgBox Err.Description, vbCritical, pcsVBProjectName
'  End Select
End Sub

Private Sub ListViewDopSter_ItemClick(ByVal Item As MSComctlLib.ListItem)
  'выводим позицию стержня если она назначена
  
  Dim oDopSter As clDopStergen
  
  'находим объект
  For Each oDopSter In pcolClDopStergny
    If oDopSter.sNaimenovanie = Item.Text Then
      Exit For
    End If
  Next
  
  TextBoxDopSterPoz = oDopSter.iPoz
  
End Sub

Private Sub ListViewPerepady_ItemClick(ByVal Item As MSComctlLib.ListItem)
  'выводим параметры перепада
    
  TextBoxHPerepada = Item.Text
  TextBoxHRostvPerepada = Item.SubItems(1)
  TextBoxWidthRostvPerepada = Item.SubItems(2)
  TextBoxKolPerepadov = Item.SubItems(3)
  TextBoxWidthPerepada = Item.SubItems(4)
  TextBoxKolRowShpilek = Item.SubItems(5)
  TextBoxDiamSter1Perepada = Item.SubItems(6)
  TextBoxKlassSter1Perepada = Item.SubItems(7)
  TextBoxGostSter1Perepada = Item.SubItems(8)
  TextBoxDiamSter2Perepada = Item.SubItems(9)
  TextBoxKlassSter2Perepada = Item.SubItems(10)
  TextBoxGostSter2Perepada = Item.SubItems(11)
  TextBoxDiamSter3Perepada = Item.SubItems(12)
  TextBoxKlassSter3Perepada = Item.SubItems(13)
  TextBoxGostSter3Perepada = Item.SubItems(14)
  TextBoxDiamSter4Perepada = Item.SubItems(15)
  TextBoxKlassSter4Perepada = Item.SubItems(16)
  TextBoxGostSter4Perepada = Item.SubItems(17)
  
End Sub

Private Sub ListViewPlosKar_ItemClick(ByVal Item As MSComctlLib.ListItem)
  'считываем данные каркаса из коллекции pcolClPlosKar
  Functions.ItemPlosKarClick Item.Text
End Sub

Public Sub ListViewPlosKarSech_ItemClick(ByVal Item As MSComctlLib.ListItem)
  'вывод параметров в поля frame FrameParamPlosSech
  
  TextBoxNSechPlosKar = Item.Text
  TextBoxWPlosKar = Item.ListSubItems(1)
  TextBoxnPlosKar = Item.ListSubItems(2)
  TextBoxn1PlosKar = Item.ListSubItems(3)
  TextBoxSPlosKar = Item.ListSubItems(4)
  TextBoxFPlosKar = Item.ListSubItems(5)
  TextBoxKlassSvyzPlosKar = Item.ListSubItems(6)
  TextBoxGOSTSvyzVerhPlosKar = Item.ListSubItems(7)
  TextBoxS1PlosKar = Item.ListSubItems(8)
  TextBoxF1PlosKar = Item.ListSubItems(9)
  TextBoxKlass1SvyzPlosKar = Item.ListSubItems(10)
  TextBoxGOSTSvyzNizPlosKar = Item.ListSubItems(11)
  
End Sub

Private Sub ListViewProsKar_ItemClick(ByVal Item As MSComctlLib.ListItem)
  'считываем данные каркаса из коллекции pcolClProsKar
  Functions.ItemProsKarClick Item.Text
End Sub

Private Sub ListViewSetky_ItemClick(ByVal Item As MSComctlLib.ListItem)
  'выводим параметры выбранной сетки
  
  Dim oSetka As clSetky
  
  'находим объект
  Set oSetka = pcolClSetky.Item(Item.Text)
  
  'признак обработки (если галочка стоит)
  If Item.SmallIcon = 1 Then
    'выводим параметрры сетки
    TextBoxDiam1Setky = oSetka.piDiamVertSter
    TextBoxShag1Setky = oSetka.piShagVertSter
    TextBoxN1Setky = oSetka.piKolShagovVertik
    TextBoxKlass1Setky = oSetka.psKlassVertSter
    TextBoxGost1Setky = oSetka.psGOSTVertSter
    TextBoxDiam2Setky = oSetka.piDiamHorSter
    TextBoxShag2Setky = oSetka.piShagHorSter
    TextBoxN2Setky = oSetka.piKolShagovHoris
    TextBoxKlass2Setky = oSetka.psKlassHorSter
    TextBoxGost2Setky = oSetka.psGOSTHorSter
    If oSetka.pbDopSter = True Then
      CheckBoxSterSetky.Value = True
      TextBoxDiamSterSetky = oSetka.piDiamDopSter
      TextBoxLSterSetky = oSetka.piLenDopSter
      TextBoxKolSterSetky = oSetka.piKolDopSter
      TextBoxKlassSterSetky = oSetka.psKlassDopSter
      TextBoxGostSterSetky = oSetka.psGOSTDopSter
    Else
      CheckBoxSterSetky.Value = False
    End If
  Else
    CheckBoxSterSetky.Value = False
  End If
  
End Sub

Private Sub MultiPageMain_Change()
  
  'нужно определить на какую вкладку произошло переключение
  
  '!!!!!!!!!! изменение. Касается всей процедуры. Думаю, нужно предварительную обработку сделать сразу, а не во время переключения на вкладку. После выбора объектов на чертеже.
  
  Select Case MultiPageMain.Value
    Case 0
'      sVkladka = "Настройки"
      'тут кажись делать ниче ненадо
      'настройки были считаны при инициализации формы
      'пусть вносят изменения, применяют и сохраняют
    Case 1
'      sVkladka = "Исходные данные"
      'обработка исходных данных проекта
      'считываем шифр с чертежа
      'Functions.ObrabAttributov
    Case 2
'      sVkladka = "Выбор"
      'делать ничего не надо
    Case 3
'      sVkladka = "Простр каркасы"
      If pbolObrabProsKar = False Then
         'процедура обработки блоков пространственных каркасов из коллеции выбранных блоков каркасов
         Functions.ObrabProsKar
      End If
    Case 4
'      sVkladka = "Плоские каркасы"
      If pbolObrabPlosKar = False Then
        Functions.ObrabPlosKar
      End If
    Case 5
'      sVkladka = "Сетки"
      If pbolObrabSetok = False Then
        Functions.ObrabSetok
      End If
    Case 6
'      sVkladka = "Доп стержни"
      If pbolObraDopSter = False Then
        Functions.ObrabDopSter
      End If
    Case 7
'      sVkladka = "Перепады"
      If pbolObrabPerepadov = False Then
        Functions.ObrabPerepadov
      End If
    Case 8
'      sVkladka = "Спецификации"
      Functions.ObrabSpec
  End Select
    
End Sub

Private Sub TextBoxDiam1Setky_Exit(ByVal Cancel As MSForms.ReturnBoolean)
  If Functions.ProvDiamStandard(Val(TextBoxDiam1Setky)) = False Then
    MsgBox TextBoxDiam1Setky & " - этот диаметр не применяется.", vbCritical, pcsVBProjectName
    TextBoxDiam1Setky = 8
  End If
End Sub

Private Sub TextBoxDiam2Setky_Exit(ByVal Cancel As MSForms.ReturnBoolean)
  If Functions.ProvDiamStandard(Val(TextBoxDiam2Setky)) = False Then
    MsgBox TextBoxDiam2Setky & " - этот диаметр не применяется.", vbCritical, pcsVBProjectName
    TextBoxDiam2Setky = 8
  End If
End Sub

Private Sub TextBoxDiamNizSvyzSter_Exit(ByVal Cancel As MSForms.ReturnBoolean)
  If Functions.ProvDiamStandard(Val(TextBoxDiamNizSvyzSter)) = False Then
    MsgBox TextBoxDiamNizSvyzSter & " - этот диаметр не применяется.", vbCritical, pcsVBProjectName
    TextBoxDiamNizSvyzSter = 8
  End If
End Sub

Private Sub TextBoxDiamSter1Perepada_Exit(ByVal Cancel As MSForms.ReturnBoolean)
  If Functions.ProvDiamStandard(TextBoxDiamSter1Perepada) = False Then
    MsgBox TextBoxDiamSter1Perepada & " - этот диаметр не применяется.", vbCritical, pcsVBProjectName
    TextBoxDiamSter1Perepada = pclOptions.piDiamSter1Perepada
  Else
    'pclOptions.piDiamSter1Perepada = TextBoxDiamSter1Perepada
  End If
End Sub

Private Sub TextBoxDiamSter2Perepada_Exit(ByVal Cancel As MSForms.ReturnBoolean)
  If Functions.ProvDiamStandard(Val(TextBoxDiamSter2Perepada)) = False Then
    MsgBox TextBoxDiamSter2Perepada & " - этот диаметр не применяется.", vbCritical, pcsVBProjectName
    TextBoxDiamSter2Perepada = pclOptions.piDiamSter2Perepada
  Else
    'pclOptions.piDiamSter2Perepada = TextBoxDiamSter2Perepada
  End If
End Sub

Private Sub TextBoxDiamSter3Perepada_Exit(ByVal Cancel As MSForms.ReturnBoolean)
  If Functions.ProvDiamStandard(Val(TextBoxDiamSter3Perepada)) = False Then
    MsgBox TextBoxDiamSter3Perepada & " - этот диаметр не применяется.", vbCritical, pcsVBProjectName
    TextBoxDiamSter3Perepada = pclOptions.piDiamSter1Perepada
  Else
    'pclOptions.piDiamSter3Perepada = TextBoxDiamSter3Perepada
  End If
End Sub

Private Sub TextBoxDiamSter4Perepada_Exit(ByVal Cancel As MSForms.ReturnBoolean)
  If Functions.ProvDiamStandard(Val(TextBoxDiamSter4Perepada)) = False Then
    MsgBox TextBoxDiamSter4Perepada & " - этот диаметр не применяется.", vbCritical, pcsVBProjectName
    TextBoxDiamSter4Perepada = pclOptions.piDiamSter4Perepada
  Else
    'pclOptions.piDiamSter4Perepada = TextBoxDiamSter4Perepada
  End If
End Sub

Private Sub TextBoxDiamSterSetky_Exit(ByVal Cancel As MSForms.ReturnBoolean)
  If Functions.ProvDiamStandard(Val(TextBoxDiamSterSetky)) = False Then
    MsgBox TextBoxDiamSterSetky & " - этот диаметр не применяется.", vbCritical, pcsVBProjectName
    TextBoxDiamSterSetky = 8
  End If
End Sub

Private Sub TextBoxDiamVerhSvyzSter_Exit(ByVal Cancel As MSForms.ReturnBoolean)
  If Functions.ProvDiamStandard(Val(TextBoxDiamVerhSvyzSter)) = False Then
    MsgBox TextBoxDiamVerhSvyzSter & " - этот диаметр не применяется.", vbCritical, pcsVBProjectName
    TextBoxDiamVerhSvyzSter = 8
  End If
  
End Sub

Private Sub TextBoxDopSterPoz_Change()
  Dim iNum As Integer
  
  iNum = Val(TextBoxDopSterPoz)
  If iNum <> 0 Then
    TextBoxDopSterPoz = iNum
  Else
    TextBoxDopSterPoz = 1
  End If
End Sub

Private Sub TextBoxF1PlosKar_Exit(ByVal Cancel As MSForms.ReturnBoolean)
  If Functions.ProvDiamStandard(Val(TextBoxF1PlosKar)) = False Then
    MsgBox TextBoxF1PlosKar & " - этот диаметр не применяется.", vbCritical, pcsVBProjectName
    TextBoxF1PlosKar = 8
  End If
End Sub

Private Sub TextBoxFPlosKar_Exit(ByVal Cancel As MSForms.ReturnBoolean)
  If Functions.ProvDiamStandard(Val(TextBoxFPlosKar)) = False Then
    MsgBox TextBoxFPlosKar & " - этот диаметр не применяется.", vbCritical, pcsVBProjectName
    TextBoxFPlosKar = 8
  End If
End Sub

Private Sub TextBoxGost1Setky_Exit(ByVal Cancel As MSForms.ReturnBoolean)
  If TextBoxGost1Setky = "" Then TextBoxGost1Setky = pclOptions.psGOSTDopStergDef
End Sub

Private Sub TextBoxGost2Setky_Exit(ByVal Cancel As MSForms.ReturnBoolean)
  If TextBoxGost2Setky = "" Then TextBoxGost2Setky = pclOptions.psGOSTDopStergDef
End Sub

Private Sub TextBoxGOSTNizArm_Exit(ByVal Cancel As MSForms.ReturnBoolean)
  If TextBoxGOSTNizArm = "" Then TextBoxGOSTNizArm = pclOptions.psGOSTNizDef
End Sub

Private Sub TextBoxGOSTPopArm_Exit(ByVal Cancel As MSForms.ReturnBoolean)
  If TextBoxGOSTPopArm = "" Then TextBoxGOSTPopArm = pclOptions.psGOSTPopDef
End Sub

Private Sub TextBoxGostSter1Perepada_Exit(ByVal Cancel As MSForms.ReturnBoolean)
  If TextBoxGostSter1Perepada = "" Then
    TextBoxGostSter1Perepada = pclOptions.psGostSter1Perepada
  Else
    'pclOptions.psGostSter1Perepada = TextBoxGostSter1Perepada
  End If
End Sub

Private Sub TextBoxGostSter2Perepada_Exit(ByVal Cancel As MSForms.ReturnBoolean)
  If TextBoxGostSter2Perepada = "" Then
    TextBoxGostSter2Perepada = pclOptions.psGostSter2Perepada
  Else
    'pclOptions.psGostSter2Perepada = TextBoxGostSter2Perepada
  End If
End Sub

Private Sub TextBoxGostSter3Perepada_Exit(ByVal Cancel As MSForms.ReturnBoolean)
  If TextBoxGostSter3Perepada = "" Then
    TextBoxGostSter3Perepada = pclOptions.psGostSter3Perepada
  Else
    'pclOptions.psGostSter3Perepada = TextBoxGostSter3Perepada
  End If
End Sub

Private Sub TextBoxGostSter4Perepada_Exit(ByVal Cancel As MSForms.ReturnBoolean)
  If TextBoxGostSter4Perepada = "" Then
    TextBoxGostSter4Perepada = pclOptions.psGostSter4Perepada
  Else
    'pclOptions.psGostSter4Perepada = TextBoxGostSter4Perepada
  End If
End Sub

Private Sub TextBoxGostSterSetky_Exit(ByVal Cancel As MSForms.ReturnBoolean)
  If TextBoxGostSterSetky = "" Then TextBoxGostSterSetky = pclOptions.psGOSTDopStergDef
End Sub

Private Sub TextBoxGOSTSvyzNizArm_Exit(ByVal Cancel As MSForms.ReturnBoolean)
  If TextBoxGOSTSvyzNizArm = "" Then TextBoxGOSTSvyzNizArm = pclOptions.psGOSTSvyzNizDef
End Sub

Private Sub TextBoxGOSTSvyzNizPlosKar_Exit(ByVal Cancel As MSForms.ReturnBoolean)
  If TextBoxGOSTSvyzNizPlosKar = "" Then TextBoxGOSTSvyzNizPlosKar = pclOptions.psGOSTSvyzNizDef
End Sub

Private Sub TextBoxGOSTSvyzVerhArm_Exit(ByVal Cancel As MSForms.ReturnBoolean)
  If TextBoxGOSTSvyzVerhArm = "" Then TextBoxGOSTSvyzVerhArm = pclOptions.psGOSTSvyzVerhDef
End Sub

Private Sub TextBoxGOSTSvyzVerhPlosKar_Exit(ByVal Cancel As MSForms.ReturnBoolean)
  If TextBoxGOSTSvyzVerhPlosKar = "" Then TextBoxGOSTSvyzVerhPlosKar = pclOptions.psGOSTSvyzVerhDef
End Sub

Private Sub TextBoxGOSTVerhArm_Exit(ByVal Cancel As MSForms.ReturnBoolean)
  If TextBoxGOSTVerhArm = "" Then TextBoxGOSTVerhArm = pclOptions.psGOSTVerhDef
End Sub

Private Sub TextBoxHeightRost_Exit(ByVal Cancel As MSForms.ReturnBoolean)
  TextBoxHeightRost = CInt(Val(TextBoxHeightRost))
  If CInt(TextBoxHeightRost) < 200 Then
    MsgBox "Минимальная высота ростверка 200", vbCritical, pcsVBProjectName
    TextBoxHeightRost = pclOptions.iHeightRostDef
  End If
End Sub

Private Sub TextBoxHPerepada_Exit(ByVal Cancel As MSForms.ReturnBoolean)
  
  TextBoxHPerepada = CInt(Val(TextBoxHPerepada))
  If Val(TextBoxHPerepada) = 0 Then
    MsgBox "Введите высоту перепада", vbExclamation, pcsVBProjectName
    TextBoxHPerepada = "1200"
  End If
  
  'если высота перепада больше 1200 то два ряда шпилек
  If Val(TextBoxHPerepada) >= 1200 Then
    TextBoxKolRowShpilek = "2"
  ElseIf Val(TextBoxHPerepada) >= 900 Then
    TextBoxKolRowShpilek = "1"
  Else
    TextBoxKolRowShpilek = "0"
  End If
End Sub

Private Sub TextBoxHPlosKar_Exit(ByVal Cancel As MSForms.ReturnBoolean)
  TextBoxHPlosKar = CInt(Val(TextBoxHPlosKar))
  If CInt(TextBoxHPlosKar) < 200 Then
    MsgBox "Минимальная высота ростверка 200", vbCritical, pcsVBProjectName
    TextBoxHPlosKar = 400
  End If
End Sub

Private Sub TextBoxHRostvPerepada_Exit(ByVal Cancel As MSForms.ReturnBoolean)
  TextBoxHRostvPerepada = CInt(Val(TextBoxHRostvPerepada))
  If CInt(TextBoxHRostvPerepada) < 200 Then
    MsgBox "Минимальная высота ростверка 400", vbCritical, pcsVBProjectName
    TextBoxHRostvPerepada = 400
  End If
End Sub

Private Sub TextBoxHvost0_Exit(ByVal Cancel As MSForms.ReturnBoolean)
  If Not IsNumeric(TextBoxHvost0) Then
      MsgBox "Нужно ввести число", vbCritical, pcsVBProjectName
      TextBoxLenSech = "600"
   End If
End Sub

Private Sub TextBoxKlass1Setky_Exit(ByVal Cancel As MSForms.ReturnBoolean)
  If TextBoxKlass1Setky = "" Then TextBoxKlass1Setky = pclOptions.psKlassDopStergDef
End Sub

Private Sub TextBoxKlass1SvyzPlosKar_Exit(ByVal Cancel As MSForms.ReturnBoolean)
  If TextBoxKlass1SvyzPlosKar = "" Then TextBoxKlass1SvyzPlosKar = pclOptions.psKlassSvyzNizDef
End Sub

Private Sub TextBoxKlass2Setky_Exit(ByVal Cancel As MSForms.ReturnBoolean)
  If TextBoxKlass2Setky = "" Then TextBoxKlass2Setky = pclOptions.psKlassDopStergDef
End Sub

Private Sub TextBoxKlassNizArm_Exit(ByVal Cancel As MSForms.ReturnBoolean)
  If TextBoxKlassNizArm = "" Then TextBoxKlassNizArm = pclOptions.psKlassNizDef
End Sub

Private Sub TextBoxKlassPopArm_Exit(ByVal Cancel As MSForms.ReturnBoolean)
  If TextBoxKlassPopArm = "" Then TextBoxKlassPopArm = pclOptions.psKlassPopDef
End Sub

Private Sub TextBoxKlassSter1Perepada_Exit(ByVal Cancel As MSForms.ReturnBoolean)
  If TextBoxKlassSter1Perepada = "" Then
    TextBoxKlassSter1Perepada = pclOptions.psKlassSter1Perepada
  Else
    'pclOptions.psKlassSter1Perepada = TextBoxKlassSter1Perepada
  End If
End Sub

Private Sub TextBoxKlassSter2Perepada_Exit(ByVal Cancel As MSForms.ReturnBoolean)
  If TextBoxKlassSter2Perepada = "" Then
    TextBoxKlassSter2Perepada = pclOptions.psKlassSter2Perepada
  Else
    'pclOptions.psKlassSter2Perepada = TextBoxKlassSter2Perepada
  End If
End Sub

Private Sub TextBoxKlassSter3Perepada_Exit(ByVal Cancel As MSForms.ReturnBoolean)
  If TextBoxKlassSter3Perepada = "" Then
    TextBoxKlassSter3Perepada = pclOptions.psKlassSter3Perepada
  Else
    'pclOptions.psKlassSter3Perepada = TextBoxKlassSter3Perepada
  End If
End Sub

Private Sub TextBoxKlassSter4Perepada_Exit(ByVal Cancel As MSForms.ReturnBoolean)
  If TextBoxKlassSter4Perepada = "" Then
    TextBoxKlassSter4Perepada = pclOptions.psKlassSter4Perepada
  Else
    'pclOptions.psKlassSter4Perepada = TextBoxKlassSter4Perepada
  End If
End Sub

Private Sub TextBoxKlassSterSetky_Exit(ByVal Cancel As MSForms.ReturnBoolean)
  If TextBoxKlassSterSetky = "" Then TextBoxKlassSterSetky = pclOptions.psKlassDopStergDef
End Sub

Private Sub TextBoxKlassSvyzNizArm_Exit(ByVal Cancel As MSForms.ReturnBoolean)
  If TextBoxKlassSvyzNizArm = "" Then TextBoxKlassSvyzNizArm = pclOptions.psKlassSvyzNizDef
End Sub

Private Sub TextBoxKlassSvyzPlosKar_Exit(ByVal Cancel As MSForms.ReturnBoolean)
  If TextBoxKlassSvyzPlosKar = "" Then TextBoxKlassSvyzPlosKar = pclOptions.psKlassSvyzVerhDef
End Sub

Private Sub TextBoxKlassSvyzVerhArm_Exit(ByVal Cancel As MSForms.ReturnBoolean)
  If TextBoxKlassSvyzVerhArm = "" Then TextBoxKlassSvyzVerhArm = pclOptions.psKlassSvyzVerhDef
End Sub

Private Sub TextBoxKlassVerhArm_Exit(ByVal Cancel As MSForms.ReturnBoolean)
  If TextBoxKlassVerhArm = "" Then TextBoxKlassVerhArm = pclOptions.psKlassVerhDef
End Sub

Private Sub TextBoxKlassVerhPlosKar_Exit(ByVal Cancel As MSForms.ReturnBoolean)
  If TextBoxKlassVerhArm = "" Then TextBoxKlassVerhArm = pclOptions.psKlassVerhDef
End Sub

Private Sub TextBoxKolPerepadov_Exit(ByVal Cancel As MSForms.ReturnBoolean)
  TextBoxKolPerepadov = CInt(TextBoxKolPerepadov)
  If CInt(TextBoxKolPerepadov) <= 0 Then
    MsgBox "Минимальное кол-во перепадов 1", vbCritical, pcsVBProjectName
    TextBoxKolPerepadov = 1
  End If
End Sub

Private Sub TextBoxKolRowShpilek_Exit(ByVal Cancel As MSForms.ReturnBoolean)
  TextBoxKolRowShpilek = CInt(TextBoxKolRowShpilek)
  If Val(TextBoxKolRowShpilek) < 0 Then
    TextBoxKolRowShpilek = "0"
  End If
End Sub

Private Sub TextBoxKolSterSetky_Exit(ByVal Cancel As MSForms.ReturnBoolean)
  TextBoxKolSterSetky = CInt(TextBoxKolSterSetky)
  If CInt(TextBoxKolSterSetky) < 1 Then
    MsgBox "Минимальное кол-во стержней - 1", vbExclamation, pcsVBProjectName
    TextBoxKolSterSetky = "9"
  End If
End Sub

Private Sub TextBoxLenSech_Exit(ByVal Cancel As MSForms.ReturnBoolean)
  TextBoxLenSech = CInt(Val(TextBoxLenSech))
  If CInt(TextBoxLenSech) < 400 Then
    MsgBox "Минимальная ширина ростверка 400"
    TextBoxLenSech = 500
  End If
End Sub

Private Sub TextBoxLSterSetky_Exit(ByVal Cancel As MSForms.ReturnBoolean)
  TextBoxLSterSetky = CInt(Val(TextBoxLSterSetky))
  If CInt(TextBoxLSterSetky) < 200 Then
    MsgBox "Минимальная длина 200", vbExclamation, pcsVBProjectName
    TextBoxLSterSetky = "330"
  End If
End Sub

Private Sub TextBoxn1PlosKar_Exit(ByVal Cancel As MSForms.ReturnBoolean)
  TextBoxn1PlosKar = CInt(Val(TextBoxn1PlosKar))
  If CInt(TextBoxn1PlosKar) = 0 Then
    TextBoxn1PlosKar = "1"
  End If
End Sub

Private Sub TextBoxN1Setky_Exit(ByVal Cancel As MSForms.ReturnBoolean)
  TextBoxN1Setky = CInt(Val(TextBoxN1Setky))
  If CInt(TextBoxN1Setky) < 1 Then
    MsgBox "Минимальное кол-во шагов - 1", vbExclamation, pcsVBProjectName
    TextBoxN1Setky = "5"
  End If
End Sub

Private Sub TextBoxN2Setky_Exit(ByVal Cancel As MSForms.ReturnBoolean)
  TextBoxN2Setky = CInt(Val(TextBoxN2Setky))
  If CInt(TextBoxN2Setky) < 1 Then
    MsgBox "Минимальное кол-во шагов - 1", vbExclamation, pcsVBProjectName
    TextBoxN2Setky = "5"
  End If
End Sub

Private Sub TextBoxNizZachBet_Exit(ByVal Cancel As MSForms.ReturnBoolean)
  TextBoxNizZachBet = CInt(Val(TextBoxNizZachBet))
  If CInt(TextBoxNizZachBet) < 20 Then
    MsgBox "Минимальное расстояние от сентра нижней рабочей арматуры до низа ростверка 20", vbCritical, pcsVBProjectName
    TextBoxNizZachBet = pclOptions.iZachBetNizDef
  End If
End Sub

Private Sub TextBoxnPlosKar_Exit(ByVal Cancel As MSForms.ReturnBoolean)
  TextBoxnPlosKar = CInt(Val(TextBoxnPlosKar))
  If CInt(TextBoxnPlosKar) = 0 Then
    TextBoxnPlosKar = "1"
  End If
End Sub

Private Sub TextBoxNSech_Change()
  If poProsKarSech.GetParamSech = False Then
    If Me.CheckBoxMarkaK.Value = False Then
      pclOptions.LoadProsKarParamSech FormSpecRost.TextBoxNSech
    Else
      'для кирпички
      pclOptions.LoadProsKarParamSech "0"
    End If
  End If
End Sub

Private Sub TextBoxNSech_Exit(ByVal Cancel As MSForms.ReturnBoolean)
  If TextBoxNSech = "" Then TextBoxNSech = 1
End Sub

Private Sub TextBoxNSechForViewPlosKar_Change()
    TextBoxNSechForViewPlosKar = CInt(Val(TextBoxNSechForViewPlosKar))
  If CInt(TextBoxNSechForViewPlosKar) = 0 Then
    MsgBox "Введите номер сечения.", vbExclamation, pcsVBProjectName
    TextBoxNSechForViewPlosKar = 1
  End If
End Sub

Private Sub TextBoxNSechPlosKar_Change()
  pclOptions.LoadPlosKarParamSech
End Sub

Private Sub TextBoxNSechPlosKar_Exit(ByVal Cancel As MSForms.ReturnBoolean)
  If TextBoxNSechPlosKar = "" Then TextBoxNSechPlosKar = 1
End Sub

Private Sub TextBoxS1PlosKar_Exit(ByVal Cancel As MSForms.ReturnBoolean)
  TextBoxS1PlosKar = CInt(TextBoxS1PlosKar)
  If CInt(TextBoxS1PlosKar) < 50 Then
    MsgBox "Минимальная шаг связевого стержня 50", vbExclamation, pcsVBProjectName
    TextBoxS1PlosKar = 300
  End If
End Sub

Private Sub TextBoxShag1Setky_Exit(ByVal Cancel As MSForms.ReturnBoolean)
  TextBoxShag1Setky = CInt(TextBoxShag1Setky)
  If CInt(TextBoxShag1Setky) < 50 Then
    MsgBox "Минимальная шаг связевого стержня 50", vbExclamation, pcsVBProjectName
    TextBoxShag1Setky = 100
  End If
End Sub

Private Sub TextBoxShag2Setky_Exit(ByVal Cancel As MSForms.ReturnBoolean)
  TextBoxShag2Setky = CInt(TextBoxShag2Setky)
  If CInt(TextBoxShag2Setky) < 50 Then
    MsgBox "Минимальная шаг связевого стержня 50", vbExclamation, pcsVBProjectName
    TextBoxShag2Setky = 100
  End If
End Sub

Private Sub TextBoxShagDopPopPlosKar_Exit(ByVal Cancel As MSForms.ReturnBoolean)
  TextBoxShagDopPopPlosKar = CInt(TextBoxShagDopPopPlosKar)
  If CInt(TextBoxShagDopPopPlosKar) < 50 Then
    MsgBox "Минимальная шаг доп.поп.стержня 50", vbExclamation, pcsVBProjectName
    TextBoxShagDopPopPlosKar = pclOptions.piShagDopPopSterDef
  End If
End Sub

Private Sub TextBoxShagDopPopSter_Exit(ByVal Cancel As MSForms.ReturnBoolean)
  TextBoxShagDopPopSter = CInt(TextBoxShagDopPopSter)
  If CInt(TextBoxShagDopPopSter) < 50 Then
    MsgBox "Минимальная шаг доп.поп.стержня 50", vbExclamation, pcsVBProjectName
    TextBoxShagDopPopSter = pclOptions.piShagDopPopSterDef
  End If
End Sub

Private Sub TextBoxShagNizSvyzSter_Exit(ByVal Cancel As MSForms.ReturnBoolean)
  TextBoxShagNizSvyzSter = CInt(TextBoxShagNizSvyzSter)
  If CInt(TextBoxShagNizSvyzSter) < 50 Then
    MsgBox "Минимальная шаг связевого стержня 50", vbExclamation, pcsVBProjectName
    TextBoxShagNizSvyzSter = 300
  End If
End Sub

Private Sub TextBoxShagVerhSvyzSter_Exit(ByVal Cancel As MSForms.ReturnBoolean)
  TextBoxShagVerhSvyzSter = CInt(TextBoxShagVerhSvyzSter)
  If CInt(TextBoxShagVerhSvyzSter) < 50 Then
    MsgBox "Минимальная шаг связевого стержня 50", vbExclamation, pcsVBProjectName
    TextBoxShagVerhSvyzSter = 300
  End If
End Sub

Private Sub TextBoxSPlosKar_Exit(ByVal Cancel As MSForms.ReturnBoolean)
  TextBoxSPlosKar = CInt(TextBoxSPlosKar)
  If CInt(TextBoxSPlosKar) < 50 Then
    MsgBox "Минимальная шаг связевого стержня 50", vbExclamation, pcsVBProjectName
    TextBoxSPlosKar = 300
  End If
End Sub

Private Sub TextBoxUsDiamNizArm_Exit(ByVal Cancel As MSForms.ReturnBoolean)
  If Functions.ProvDiamStandard(Val(TextBoxUsDiamNizArm)) = False Then
    MsgBox TextBoxUsDiamNizArm & " - этот диаметр не применяется.", vbExclamation, pcsVBProjectName
    TextBoxUsDiamNizArm = 8
  End If
End Sub

Private Sub TextBoxUsDiamVerhArm_Exit(ByVal Cancel As MSForms.ReturnBoolean)
  If Functions.ProvDiamStandard(Val(TextBoxUsDiamVerhArm)) = False Then
    MsgBox TextBoxUsDiamVerhArm & " - этот диаметр не применяется.", vbExclamation, pcsVBProjectName
    TextBoxUsDiamVerhArm = 8
  End If
End Sub

Private Sub TextBoxUsGOSTNizArm_Exit(ByVal Cancel As MSForms.ReturnBoolean)
  If TextBoxUsGOSTNizArm = "" Then TextBoxUsGOSTNizArm = pclOptions.psGOSTSvyzNizDef
End Sub

Private Sub TextBoxUsGOSTVerhArm_Exit(ByVal Cancel As MSForms.ReturnBoolean)
  If TextBoxUsGOSTVerhArm = "" Then TextBoxUsGOSTVerhArm = pclOptions.psGOSTSvyzVerhDef
End Sub

Private Sub TextBoxUsKlassNizArm_Exit(ByVal Cancel As MSForms.ReturnBoolean)
  If TextBoxUsKlassNizArm = "" Then TextBoxUsKlassNizArm = pclOptions.psKlassSvyzNizDef
End Sub

Private Sub TextBoxUsKlassVerhArm_Exit(ByVal Cancel As MSForms.ReturnBoolean)
  If TextBoxUsKlassVerhArm = "" Then TextBoxUsKlassVerhArm = pclOptions.psKlassSvyzVerhDef
End Sub

Private Sub TextBoxUsKolsech_Change()
  Dim iKol As Integer
  iKol = Me.ListViewProsKar.SelectedItem.SubItems(1)
  
  TextBoxUsKolSech = CInt(Val(TextBoxUsKolSech))
  If CInt(TextBoxUsKolSech) > iKol Then
    MsgBox "Количество усиливаемых каркасов не может превышать общее количество этих каркасов", vbExclamation, pcsVBProjectName
    TextBoxUsKolSech = iKol
  End If
  
End Sub

Private Sub TextBoxUsLenSech_Exit(ByVal Cancel As MSForms.ReturnBoolean)
  TextBoxUsLenSech = CInt(Val(TextBoxUsLenSech))
  If CInt(TextBoxUsLenSech) < 400 Then
    MsgBox "Минимальная ширина ростверка 400", vbExclamation, pcsVBProjectName
    TextBoxUsLenSech = 1050
  End If
End Sub

Private Sub TextBoxUsShagNizArm_Exit(ByVal Cancel As MSForms.ReturnBoolean)
  TextBoxUsShagNizArm = CInt(Val(TextBoxUsShagNizArm))
  If CInt(TextBoxUsShagNizArm) < 50 Then
    MsgBox "Минимальный шаг усиливающих стержней 50", vbExclamation, pcsVBProjectName
    TextBoxUsShagNizArm = 300
  End If
End Sub

Private Sub TextBoxUsShagVerhArm_Exit(ByVal Cancel As MSForms.ReturnBoolean)
  TextBoxUsShagVerhArm = CInt(Val(TextBoxUsShagVerhArm))
  If CInt(TextBoxUsShagVerhArm) < 50 Then
    MsgBox "Минимальный шаг усиливающих стержней 50", vbExclamation, pcsVBProjectName
    TextBoxUsShagVerhArm = 300
  End If
End Sub

Private Sub TextBoxVerhZachBet_Exit(ByVal Cancel As MSForms.ReturnBoolean)
  TextBoxVerhZachBet = CInt(Val(TextBoxVerhZachBet))
  If CInt(TextBoxVerhZachBet) < 20 Then
    MsgBox "Минимальное расстояние от сентра верхней рабочей арматуры до верха ростверка 20", vbExclamation, pcsVBProjectName
    TextBoxVerhZachBet = pclOptions.iZachBetVerhDef
  End If
End Sub

Private Sub TextBoxWidthPerepada_Exit(ByVal Cancel As MSForms.ReturnBoolean)
  TextBoxWidthPerepada = CInt(Val(TextBoxWidthPerepada))
  If CInt(TextBoxWidthPerepada) < 200 Then
    MsgBox "Минимальная ширина ростверка 400", vbCritical, pcsVBProjectName
    TextBoxWidthPerepada = 500
  End If
End Sub

Private Sub TextBoxWidthRostvPerepada_Exit(ByVal Cancel As MSForms.ReturnBoolean)
  TextBoxWidthRostvPerepada = CInt(Val(TextBoxWidthRostvPerepada))
  If CInt(TextBoxWidthRostvPerepada) < 200 Then
    MsgBox "Минимальная ширина ростверка 400", vbCritical, pcsVBProjectName
    TextBoxWidthRostvPerepada = 500
  End If
End Sub

Private Sub TextBoxWPlosKar_Exit(ByVal Cancel As MSForms.ReturnBoolean)
  TextBoxWPlosKar = CInt(Val(Val(TextBoxWPlosKar)))
  If CInt(TextBoxWPlosKar) < 400 And CInt(TextBoxWPlosKar) <> 0 Then
    MsgBox "Минимальная ширина ростверка 400", vbCritical, pcsVBProjectName
    TextBoxWPlosKar = 500
  End If
End Sub

Private Sub TextBoxZachNizPlosKar_Exit(ByVal Cancel As MSForms.ReturnBoolean)
  TextBoxZachNizPlosKar = CInt(Val(TextBoxZachNizPlosKar))
  If CInt(TextBoxZachNizPlosKar) < 20 Then
    MsgBox "Минимальное расстояние от центра нижней рабочей арматуры до низа ростверка 20", vbExclamation, pcsVBProjectName
    TextBoxZachNizPlosKar = pclOptions.iZachBetNizDef
  End If
End Sub

Private Sub TextBoxZachVerhPlosKar_Exit(ByVal Cancel As MSForms.ReturnBoolean)
  TextBoxZachVerhPlosKar = CInt(Val(TextBoxZachVerhPlosKar))
  If CInt(TextBoxZachVerhPlosKar) < 20 Then
    MsgBox "Минимальное расстояние от сентра верхней рабочей арматуры до верха ростверка 20", vbExclamation, pcsVBProjectName
    TextBoxZachVerhPlosKar = pclOptions.iZachBetVerhDef
  End If
End Sub

Private Sub UserForm_Activate()
  'активация происходит не только при повторном открытии формы с кнопки
  'но и при Выборе (фрма скрывается для Selecta)
  'поэтому нужно точно определить что делать при активации
  
  On Error Resume Next
  
  'если чертеж для расчета был закрыт, то нужно обнулить данные (коллекции например)
  If Not pdocSpecRost Is Nothing Then
    Dim sName As String
    sName = pdocSpecRost.Name
    If Err Then
      Err.Clear
      'чертеж был закрыт
      mbolHide = False
      'очищаем листбоксы выбранных типов блоков и имен блоков
      ListBoxBlName.Clear
      ListBoxObjectsType.Clear
      'чтоб необрабатывались вкладки (чтоб ошибок не ловить стаями)
      pbolObrabPerepadov = True
      pbolObrabPlosKar = True
      pbolObrabProsKar = True
      'очищаем листвиевер
      ListViewProsKar.ListItems.Clear
      pbolObrabSetok = True
      pbolObraDopSter = True
      MsgBox "На вкладке выбор, нажмите выбор, и выберете блоки для расчета спец-ий.", vbInformation, pcsVBProjectName
      Exit Sub
    End If
  End If
  
  If mbolHide = True Then
    'значит это пользователь скрывал форму
    'нужно проверить коллекции с выбранными блоками
    'могут быть удаленные блоки
    '!!!!изменил 19.10.2014. Сообщение только мешает, каждый раз после скрытия и запуска программы.
    'MsgBox "Если были сделаны измененения блоков каркасов в чертеже, то рекомендуется выполнить выбор заново.", vbInformation, pcsVBProjectName
  End If
  
End Sub

Private Sub UserForm_DblClick(ByVal Cancel As MSForms.ReturnBoolean)
  About.Show
End Sub

Private Sub UserForm_Initialize()
  
  'обрабатывать то пока нечего
  pbolObrabPerepadov = True
  pbolObrabPlosKar = True
  pbolObrabProsKar = True
  pbolObrabSetok = True
  pbolObraDopSter = True
    
  'установкм для листвиевера пространственных каркасов
  ListViewProsKar.Icons = ImageListNormal
  ListViewProsKar.SmallIcons = ImageListNormal
  ListViewProsKar.ColumnHeaderIcons = ImageListNormal
  'добавляем столбцы
  ListViewProsKar.ColumnHeaders.Add , , "Название", 95, 0, 0
  ListViewProsKar.ColumnHeaders.Add , , "Кол.", 30, 2, 0
  ListViewProsKar.ColumnHeaders.Add , , "сечение", 30, 2, 0
  ListViewProsKar.ColumnHeaders.Add , , "МаркаК", 30, 2, 0
  
  'установки для листвиевера плоских каркасов
  ListViewPlosKar.Icons = ImageListNormal
  ListViewPlosKar.SmallIcons = ImageListNormal
  ListViewPlosKar.ColumnHeaderIcons = ImageListNormal
  'добавляем столбцы
  ListViewPlosKar.ColumnHeaders.Add , , "Название", 60, 0, 0
  ListViewPlosKar.ColumnHeaders.Add , , "Кол.", 30, 2, 0
  ListViewPlosKar.ColumnHeaders.Add , , "МаркаК", 30, 2, 0
  
  'установки для листвиевера параметров плоских каркасов
  'добавляем столбцы
  ListViewPlosKarSech.ColumnHeaders.Add 1, "NSech", "N", 25, 0, 0
  ListViewPlosKarSech.ColumnHeaders.Add 2, "LenSech", "W", 25, 2, 0
  ListViewPlosKarSech.ColumnHeaders.Add 3, "KolSech", "n", 25, 2, 0
  ListViewPlosKarSech.ColumnHeaders.Add 4, "KolKarInSech", "n1", 25, 2, 0
  ListViewPlosKarSech.ColumnHeaders.Add 5, "ShagVerh", "S", 25, 2, 0
  ListViewPlosKarSech.ColumnHeaders.Add 6, "DiamVerh", "Ф", 20, 2, 0
  ListViewPlosKarSech.ColumnHeaders.Add 7, "KlassVerh", "Класс верхней", 20, 2, 0
  ListViewPlosKarSech.ColumnHeaders.Add 8, "GOSTVerh", "ГОСТ верхней", 20, 2, 0
  ListViewPlosKarSech.ColumnHeaders.Add 9, "ShagNiz", "S1", 25, 2, 0
  ListViewPlosKarSech.ColumnHeaders.Add 10, "DiamNiz", "Ф1", 20, 2, 0
  ListViewPlosKarSech.ColumnHeaders.Add 11, "KlassNiz", "Класс верхней", 20, 2, 0
  ListViewPlosKarSech.ColumnHeaders.Add 12, "GOSTNiz", "ГОСТ верхней", 20, 2, 0
  
  'установки для листвиевера доп.стержней
  ListViewDopSter.SmallIcons = ImageListNormal
  ListViewDopSter.ColumnHeaders.Add , , "Наименование", 140, , 0
  ListViewDopSter.ColumnHeaders.Add , , "Кол.", 30, 2, 0
  
  'установки для листвиевера сеток
  ListViewSetky.SmallIcons = ImageListNormal
  ListViewSetky.ColumnHeaders.Add , , "Наименование", 120, , 0
  ListViewSetky.ColumnHeaders.Add , , "Кол.блоков", 65, 2, 0
  
  'установки для листвиевера перепадов
  ListViewPerepady.ColumnHeaders.Add 1, , "Высота перепада", 40, 0, 0
  ListViewPerepady.ColumnHeaders.Add 2, , "Высота ростверка", 40, 2, 0
  ListViewPerepady.ColumnHeaders.Add 3, , "Ширина ростверка", 40, 2, 0
  ListViewPerepady.ColumnHeaders.Add 4, , "Кол-во", 20, 2, 0
  ListViewPerepady.ColumnHeaders.Add 5, , "Ширина перепада", 40, 2, 0
  ListViewPerepady.ColumnHeaders.Add 6, , "Кол рядов шпилек", 40, 2, 0
  ListViewPerepady.ColumnHeaders.Add 7, , "D1", 15, 2, 0
  ListViewPerepady.ColumnHeaders.Add 8, , "Klass1", 15, 2, 0
  ListViewPerepady.ColumnHeaders.Add 9, , "Gost1", 15, 2, 0
  ListViewPerepady.ColumnHeaders.Add 10, , "D2", 15, 2, 0
  ListViewPerepady.ColumnHeaders.Add 11, , "Klass2", 15, 2, 0
  ListViewPerepady.ColumnHeaders.Add 12, , "Gost2", 15, 2, 0
  ListViewPerepady.ColumnHeaders.Add 13, , "D3", 15, 2, 0
  ListViewPerepady.ColumnHeaders.Add 14, , "Klass3", 15, 2, 0
  ListViewPerepady.ColumnHeaders.Add 15, , "Gost3", 15, 2, 0
  ListViewPerepady.ColumnHeaders.Add 16, , "D4", 15, 2, 0
  ListViewPerepady.ColumnHeaders.Add 17, , "Klass4", 15, 2, 0
  ListViewPerepady.ColumnHeaders.Add 18, , "Gost4", 15, 2, 0
  
  'фамиолиЯ пользователя
  FormSpecRost.TextBoxFam6 = psUserName
  
  'созание класса для хранения настроек
  Set pclOptions = New clOptions
  
  'загрузка настроек из ини
  pclOptions.LoadOptionsFromIni
  'заполнение вкладки настроек
  
  
  'устанавливаем начальную вкладку мультипайджа
  MultiPageMain.Value = 2
  
  'создаем объект параметров применяемых сечений
  Set poProsKarSech = New clProsKarSech
  
End Sub

Private Sub UserForm_Terminate()
'  'сохранение настроек в ини
'  pclOptions.SaveOptionsToIni
End Sub

Private Sub cmbSaveForShtamp_Click()
  'сохранение настроек исходных данных
  pclOptions.SaveForShtamp
  pclOptions.SaveOptionsToIni
End Sub

Attribute VB_Name = "FormSpleshLoadedRaschet"
Attribute VB_Base = "0{6607B04E-166B-4955-BE90-66458EA4A538}{69A204B8-71B1-41DB-8FEA-A551A1C25FA3}"
Attribute VB_GlobalNameSpace = False
Attribute VB_Creatable = False
Attribute VB_PredeclaredId = True
Attribute VB_Exposed = False
Attribute VB_TemplateDerived = False
Attribute VB_Customizable = False
Option Explicit

Private Sub UserForm_Activate()
   'Задержка показа формы 10 сек
   Dim dStart As Double
   dStart = Timer
   Do Until Timer - dStart > 10
      Me.Hide
   Loop
End Sub

Private Sub UserForm_Click()

End Sub

Attribute VB_Name = "FormaFreezeBlock"
Attribute VB_Base = "0{1E3040D1-173B-4204-9418-C9908A04303D}{3DBECFE0-6B03-40D4-8BB9-C12A9C15AE57}"
Attribute VB_GlobalNameSpace = False
Attribute VB_Creatable = False
Attribute VB_PredeclaredId = True
Attribute VB_Exposed = False
Attribute VB_TemplateDerived = False
Attribute VB_Customizable = False
Option Explicit

  Dim dLeft As Double
  Dim dTop As Double
  Dim colBlInLayer As New Collection
  
Private Sub cmbExit_Click()
  End
End Sub

Private Sub cmbOK_Click()
   Hide
End Sub

Private Sub cmbStop_Click()
  'если уже была остановлена прога
  If cmbStop.Caption = "Закрыть" Then
    Me.Hide
    Unload Me
    Exit Sub
  End If
  cmbStop.Caption = "Закрыть"
  cmbOK.Visible = False
  dLeft = Me.Left
  dTop = Me.top
  Me.Hide
  Me.Show vbModeless
  Me.Left = dLeft
  Me.top = dTop
End Sub

Private Sub cmbView_Click()
   'подсвечиваем и зуммируем выбранный блок
   
   Dim objBlock As AcadBlockReference
   Dim i As Integer
   Dim index As Integer
   Dim vMax As Variant
   Dim vMin As Variant
   
   On Error GoTo Ошибка
   
   pdocSpecRost.Activate
   
   If ListBoxLayers.ListIndex = -1 Then
    MsgBox "Не выбран слой!", vbExclamation, pcsVBProjectName
    Exit Sub
   End If
   index = ListBoxBlocks.ListIndex
   If index = -1 Then
    MsgBox "Не выбран блок!", vbExclamation, pcsVBProjectName
    Exit Sub
   End If
   
  'находим блок в коллекции по индексу
  Set objBlock = colBlInLayer.Item(index + 1)
  objBlock.Highlight True
  objBlock.GetBoundingBox vMin, vMax
  ZoomWindow vMin, vMax

Exit Sub
Ошибка:
   If Err.Number = -2145386420 Then
      MsgBox "Объект был стерт"
      colBlInLayer.Remove index + 1
      ListBoxBlocks.RemoveItem index
   Else
      MsgBox Err.Description
   End If
   
End Sub

Private Sub ListBoxLayers_Change()
   'Для выбранного слоя отображаем блоки
   Dim objBlock As AcadBlockReference
   Set colBlInLayer = Nothing
   Dim i As Integer
   
   On Error Resume Next
   
   'отбирпем блоки на этом слое в коллецию colBlInLayer
   i = 1
   For Each objBlock In pcolBlOnFreezeLayer
    If objBlock.Layer = ListBoxLayers Then
      If Not Err Then
        colBlInLayer.Add objBlock
      Else
        'блок был удален
        pcolBlOnFreezeLayer.Remove i
        i = i - 1
        Err.Clear
      End If
      i = i + 1
    End If
   Next
   
   On Error GoTo 0
   
   'сортируем
   Functions.SortyrBlInColByName colBlInLayer
   
   'заполняем листбокс блоков
   ListBoxBlocks.Clear
   For Each objBlock In colBlInLayer
    ListBoxBlocks.AddItem objBlock.Name
   Next
   
End Sub

Private Sub UserForm_Activate()
  
  Dim oBlRef As AcadBlockReference
  Dim sLayer As Variant
  Dim colFreezeLayer As New Collection
  
  On Error Resume Next
  
  'заполняем листбокс замороженных слоев
  For Each oBlRef In pcolBlOnFreezeLayer
     colFreezeLayer.Add oBlRef.Layer, oBlRef.Layer
  Next
  ListBoxLayers.Clear
  For Each sLayer In colFreezeLayer
    ListBoxLayers.AddItem sLayer
  Next
  
End Sub

Attribute VB_Name = "FormaProverky"
Attribute VB_Base = "0{B8F05D54-BCFA-42B0-88C0-7789FCF5417F}{3B147397-3C91-487E-A3F7-2F3DE1AD52DD}"
Attribute VB_GlobalNameSpace = False
Attribute VB_Creatable = False
Attribute VB_PredeclaredId = True
Attribute VB_Exposed = False
Attribute VB_TemplateDerived = False
Attribute VB_Customizable = False
Option Explicit
    
  Dim dLeft As Double
  Dim dTop As Double
  
   'тип текущего списка блоков
   Enum ListBoxType
      Nalogenie = 0
      NeKarkasy = 1
   End Enum
   
   Dim intListBoxType As Integer

Private Sub cmbExit_Click()
   End
End Sub


Private Sub cmbNalog_Click()
  Dim objBlock As AcadBlockReference
  Dim i As Integer
  'могут быть удаленные блоки
  On Error Resume Next
  
   ListBoxBlocks.Clear

   'вывести список наложенных блоков
   For Each objBlock In pcolBlDublicates
      ListBoxBlocks.AddItem objBlock.Name
      If Err Then
        'блок был удален
        pcolBlDublicates.Remove i
        i = i - 1
        Err.Clear
      End If
      i = i + 1
   Next
   
   intListBoxType = ListBoxType.Nalogenie
   
   LabelText = "Дублирующиеся блоки"
   
End Sub

Private Sub cmbNeKarkasy_Click()
   Dim objBlock As AcadBlockReference

   ListBoxBlocks.Clear

   'вывести список наложенных блоков
   For Each objBlock In pcolNeoprBlock
      'надеюсь индексы совпадут
      ListBoxBlocks.AddItem objBlock.Name
   Next
   intListBoxType = ListBoxType.NeKarkasy
   cmbView.Enabled = True
   
   LabelText = "Блоки с атрибутом Конструкции = Ростверк, но неопределенные как каркасы!"
   
End Sub

Private Sub cmbOK_Click()
   'все по новой
   
   Dim bolYes As Boolean
      
   If MsgBox("Продолжить не учитывая эти ошибки?", vbQuestion + vbYesNo) = vbNo Then
      Exit Sub
   End If

   Hide
End Sub


Private Sub cmbStop_Click()
   'если уже была остановлена прога
  If cmbStop.Caption = "Закрыть" Then
    Me.Hide
    Unload Me
    Exit Sub
  End If
  cmbStop.Caption = "Закрыть"
  cmbOK.Visible = False
  dLeft = Me.Left
  dTop = Me.top
  Me.Hide
  Me.Show vbModeless
  Me.Left = dLeft
  Me.top = dTop
End Sub

Private Sub cmbView_Click()
      
   Dim objBlock As AcadBlockReference
   Dim index As Integer
   Dim vMin As Variant
   Dim vMax As Variant
   
   On Error GoTo HasError
   
   pdocSpecRost.Activate
   
   index = ListBoxBlocks.ListIndex
   If index = -1 Then Exit Sub
   
   index = index + 1
   Select Case intListBoxType
      Case ListBoxType.Nalogenie
         Set objBlock = pcolBlDublicates.Item(index)
   End Select
   
   objBlock.Highlight True
   objBlock.GetBoundingBox vMin, vMax
   ZoomWindow vMin, vMax

Exit Sub
   
HasError:
   Select Case Err.Number
      Case -2145386420
         MsgBox "Блок был удален", vbCritical
         Select Case intListBoxType
            Case ListBoxType.Nalogenie
               pcolBlDublicates.Remove (index)
         End Select
         ListBoxBlocks.RemoveItem index - 1
      Case Else
         MsgBox Err.Description, vbCritical
   End Select
    
End Sub


Private Sub UserForm_Activate()
   'проверяем коллекции блоков с ошибками и отображаем кнопки
      
   Dim bolOk As Boolean
   
   On Error GoTo HasError
   
   'дубли
   If pcolBlDublicates.Count <> 0 Then
      'показываем кнопку с дублирующимися блоками
      cmbNalog.Visible = True
      bolOk = True
      'отсортировать блоки в коллекции
      Call Functions.SortyrBlInColByName(pcolBlDublicates)
   End If
   
   'неопределенные как каркасы
'   If colBlNeKarkas.Count <> 0 Then
'      'показываем кнопку с дублирующимися блоками
'      cmbNeKarkasy.Visible = True
'      bolOk = True
'      'отсортировать блоки в коллекции
'      Call DopFunction.SortyrBlInCol(colBlNeKarkas)
'   End If
   
   'если нет ни одного списка, то скрываеми его
   If bolOk = False Then
      LabelListText.Visible = False
      ListBoxBlocks.Visible = False
   End If
   
Exit Sub
HasError:
   MsgBox Err.Description, vbCritical, pcsVBProjectName
   
End Sub

Attribute VB_Name = "Functions"
Option Explicit

   Public psTitulPost1 As String
   Public psTitulPost2 As String
   Public psTitulPost3 As String
   Public psTitulFam1 As String
   Public psTitulFam2  As String
   Public psTitulFam3 As String
   Public psShtampPost1 As String
   Public psShtampPost2 As String
   Public psShtampPost3 As String
   Public psShtampPost4 As String
   Public psShtampPost5  As String
   Public psShtampPost6  As String
   Public psShtampFam1  As String
   Public psShtampFam2  As String
   Public psShtampFam3  As String
   Public psShtampFam4  As String
   Public psShtampFam5  As String
   Public psShtampFam6  As String

Public Function GetSelSet(strSelName As String) As AcadSelectionSet
   'возвращает набор, с заданным именем
   'если набор с таким именем был, он очищается
   
   On Error GoTo HasError
   Set GetSelSet = ThisDrawing.SelectionSets.Item(strSelName)
   GetSelSet.Clear
   
Exit Function

HasError:
   Set GetSelSet = ThisDrawing.SelectionSets.Add(strSelName)
   
End Function

Public Function ProvBlInFreezeLayer()
  'проверка блоков текущего чертежа определенного типа на замороженных слоях
  
  Dim oLayer As AcadLayer
  Dim colFreezeLayer As New Collection
  Dim selSet As AcadSelectionSet
  Dim oEnt As AcadEntity
  Dim oBlRef As AcadBlockReference
  Dim vAtr As Variant
  Dim intCode() As Integer
  Dim varDate() As Variant
  Dim bolKarConstr As Boolean
  Dim bolKarAtr As Boolean
  Dim sBlName As String
  Dim i As Integer
  
  'очищаем коллекцию замороженных блоков
  Set pcolBlOnFreezeLayer = Nothing
  
  'определяем замороженные слои, и заносим в коллекцию
  For Each oLayer In ThisDrawing.Layers
    If oLayer.Freeze = True Then
      colFreezeLayer.Add oLayer
    End If
  Next
  
  If colFreezeLayer.Count = 0 Then Exit Function
  
  'состовляем массив фильтров
  ReDim intCode(colFreezeLayer.Count + 2)
  ReDim varDate(colFreezeLayer.Count + 2)
  intCode(0) = 0: varDate(0) = "insert"
  'определяем фильтр по слоям
  intCode(1) = -4: varDate(1) = "<OR"
  i = 2
  For Each oLayer In colFreezeLayer
    intCode(i) = 8: varDate(i) = oLayer.Name
    i = i + 1
  Next
  intCode(i) = -4: varDate(i) = "OR>"
  
  Set selSet = Functions.GetSelSet("BlockOnFreezeLayer")
  
  'выбираем блоки на замороженных слоях
  selSet.Select acSelectionSetAll, , , intCode, varDate
  
  'определяем боки для спец-ий и заносим в коллекцию замороженных блоков
  For Each oEnt In selSet
    'если это блок
    If TypeOf oEnt Is AcadBlockReference Then
      Set oBlRef = oEnt
      
      sBlName = oBlRef.Name
      
      If oBlRef.HasAttributes = True Then
        'в имени любого каркаса есть буква К
        If InStr(sBlName, "К") Then
          'похоже это каркас, проверим атрибуты
          
          bolKarConstr = False 'входное значение, подтверждение что это каркас по атрибуту конструкции
          bolKarAtr = False 'входное значение,подтверждение что это каркас по атрибуту марки
          For Each vAtr In oBlRef.GetAttributes
            
            'если это атр конструкции
            If vAtr.Layer = pclOptions.psKarAtrConstrLayer Then
              If vAtr.TextString = pclOptions.psKarAtrConstrText Then
                'значит это блок каркаса
                bolKarConstr = True
              End If 'LCase(oAtrRef.TextString) = "ростверк" Then
            End If 'oAtrRef.Layer = "Att~Constr" Then
            
            'если это атрибут марки
            If vAtr.Layer = pclOptions.psKarAtrMarkaLayer Then
              If ProvKarBlNameAndAtrMarky(vAtr.TextString, sBlName) = True Then
                'все ок
                bolKarAtr = True
              End If
            End If
          Next 'vAtr In oBlRef.GetAttributes
          
          If bolKarConstr = True And bolKarAtr = True Then
            'добавляем блок в коллекцию блоков каркасов
            pcolBlOnFreezeLayer.Add oBlRef
          End If
          
        End If 'InStr(sBlName, "К") Then
      End If 'oBlRef.HasAttributes = True Then
      
      'сетки
      If InStr(sBlName, pclOptions.psSetkaConst & " ") <> 0 Then
        'значит это сетка!
        pcolBlOnFreezeLayer.Add oBlRef
      End If
      
      'доп.стержни
      If InStr(sBlName, pclOptions.psDopSterConst) <> 0 Then
        'значит это доп.стержень
        pcolBlOnFreezeLayer.Add oBlRef
      End If
    End If 'oEnt Is AcadBlockReference Then
  Next
  
  If pcolBlOnFreezeLayer.Count <> 0 Then
    FormaFreezeBlock.Show
  End If
  
End Function

Public Function ObrabotkaSelSet()
  'обрабатываем набор блоков("insert"), определяем объеты для спец-ий
  'и заполняем мультипадж форму FormSpecRost ("Выбор")
  
  Dim selSet As AcadSelectionSet
  Dim oEnt As AcadEntity
  Dim oBlRef As AcadBlockReference
  Dim sBlName As String
  Dim vAtr As Variant
  Dim bolKarConstr As Boolean
  Dim bolKarAtr As Boolean
  Dim bolBlTypeForSpec As Boolean 'определен ли тип блока для спец-ий
  Dim intValue As Integer
  Dim sError As String
  Dim bolMarkaK As Boolean
  Dim bolAtrMarkaK As Boolean
  
  On Error GoTo HasError
  
  'очищаем коллекции блоков
  Set pcolBlKar = Nothing
  Set pcolBlSetky = Nothing
  Set pcolBlDopSterg = Nothing
  Set pcolNeoprBlock = Nothing
  
  bolMarkaK = FormSpecRost.CheckBoxMarkaK.Value
  
  'получаем определенный набор SpecRost
  Set selSet = pdocSpecRost.SelectionSets.Item(pcsVBProjectName)
  
  FormSpecRost.LabelSelSetCount = "Всего выбрано блоков: " & selSet.Count
  
  'перебираем объекты в наборе
  For Each oEnt In selSet
    'если это блок
    If TypeOf oEnt Is AcadBlockReference Then
      bolBlTypeForSpec = False 'сбрасываем значение
      Set oBlRef = oEnt
      
      sBlName = oBlRef.Name
      
      If oBlRef.HasAttributes = True Then
        'в имени любого каркаса есть буква К
        If InStr(sBlName, "К") Then
          'похоже это каркас, проверим атрибуты
          
          bolKarConstr = False 'входное значение, подтверждение что это каркас по атрибуту конструкции
          bolKarAtr = False 'входное значение,подтверждение что это каркас по атрибуту марки
          For Each vAtr In oBlRef.GetAttributes
           If FormSpecRost.CheckBoxWithoutAtrConstr.Value = False Then
            If UCase(vAtr.Layer) = UCase(pclOptions.psKarAtrConstrLayer) Then
              If vAtr.TextString = pclOptions.psKarAtrConstrText Then
                'значит это блок каркаса
                bolKarConstr = True
              Else
                sError = sError & "Атрибут конструкции не равен - " & pclOptions.psKarAtrConstrText & vbCr
              End If 'LCase(oAtrRef.TextString) = "ростверк" Then
            End If 'oAtrRef.Layer = "Att~Constr" Then
           End If
            
            If UCase(vAtr.Layer) = UCase(pclOptions.psKarAtrMarkaLayer) Then
              If ProvKarBlNameAndAtrMarky(sBlName, vAtr.TextString) = True Then
                'все ок
                bolKarAtr = True
              Else
                sError = sError & "Имя блока не равно значению атрибута марки." & vbCr
              End If
            End If
            
            If bolMarkaK = True Then
              If UCase(vAtr.TagString) = UCase(pclOptions.psMarkaKTag) Then
                If vAtr.TextString <> "" Then
                  bolAtrMarkaK = True
                End If
              End If
            End If
            
          Next 'vAtr In oBlRef.GetAttributes
          
          If bolKarAtr = True Then
            If FormSpecRost.CheckBoxWithoutAtrConstr.Value = False Then
              If bolKarConstr = True Then
                If bolMarkaK = True Then
                  If bolAtrMarkaK = True Then
                    'добавляем блок в коллекцию блоков каркасов
                    pcolBlKar.Add oBlRef
                    bolBlTypeForSpec = True
                  End If
                Else
                  'добавляем блок в коллекцию блоков каркасов
                  pcolBlKar.Add oBlRef
                  bolBlTypeForSpec = True
                End If
              End If
            Else
              If bolMarkaK = True Then
                  If bolAtrMarkaK = True Then
                    'добавляем блок в коллекцию блоков каркасов
                    pcolBlKar.Add oBlRef
                    bolBlTypeForSpec = True
                  End If
                Else
                  'добавляем блок в коллекцию блоков каркасов
                  pcolBlKar.Add oBlRef
                  bolBlTypeForSpec = True
                End If
            End If
          End If
          
        End If 'InStr(sBlName, "К") Then
      End If 'oBlRef.HasAttributes = True Then
      
      'сетки
      If InStr(sBlName, pclOptions.psSetkaConst & " ") <> 0 Then
        'значит это сетка!
        pcolBlSetky.Add oBlRef
        bolBlTypeForSpec = True
      End If
      
      'доп.стержни
      If InStr(sBlName, pclOptions.psDopSterConst) <> 0 Then
        'значит это доп.стержень
        pcolBlDopSterg.Add oBlRef
        bolBlTypeForSpec = True
      End If
      
      If bolBlTypeForSpec = False Then
        'неопределенный блок
        pcolNeoprBlock.Add oBlRef
      End If
      
    End If 'TypeOf oEnt Is AcadBlockReference Then
  Next 'oEnt In selSet
  
  'заполняем листбокс кол-ва определнных типов объектов
  FormSpecRost.ListBoxObjectsType.AddItem "Каркасов = " & pcolBlKar.Count
  FormSpecRost.ListBoxObjectsType.AddItem "Сеток = " & pcolBlSetky.Count
  FormSpecRost.ListBoxObjectsType.AddItem "Доп.стержней = " & pcolBlDopSterg.Count
  FormSpecRost.ListBoxObjectsType.AddItem "Неопределенные = " & pcolNeoprBlock.Count
  
  'сортировка коллекций блоков
  Functions.SortyrBlInColByName pcolBlKar
  Functions.SortyrBlInColByName pcolBlSetky
  Functions.SortyrBlInColByName pcolBlDopSterg
  Functions.SortyrBlInColByName pcolNeoprBlock
  
  'раскидываем блоки по слоям
  Dim oLayer As AcadLayer
  If pcolBlKar.Count <> 0 Then
    GetLayer pclOptions.psKarLayer
    For Each oBlRef In pcolBlKar
      If oBlRef.Layer <> pclOptions.psKarLayer Then
        Set oLayer = pdocSpecRost.Layers(oBlRef.Layer)
        If oLayer.Lock = True Then
          oLayer.Lock = False
          oBlRef.Layer = pclOptions.psKarLayer
          oLayer.Lock = True
        Else
          oBlRef.Layer = pclOptions.psKarLayer
        End If
      End If
    Next
  End If
  If pcolBlSetky.Count <> 0 Then
    GetLayer pclOptions.psSetkyLayer
    For Each oBlRef In pcolBlSetky
      If oBlRef.Layer <> pclOptions.psSetkyLayer Then
        Set oLayer = pdocSpecRost.Layers(oBlRef.Layer)
        If oLayer.Lock = True Then
          oLayer.Lock = False
          oBlRef.Layer = pclOptions.psSetkyLayer
          oLayer.Lock = True
        Else
          oBlRef.Layer = pclOptions.psSetkyLayer
        End If
      End If
    Next
  End If
  If pcolBlDopSterg.Count <> 0 Then
    GetLayer pclOptions.psDopSterLayer
    For Each oBlRef In pcolBlDopSterg
      If oBlRef.Layer <> pclOptions.psDopSterLayer Then
        Set oLayer = pdocSpecRost.Layers(oBlRef.Layer)
        If oLayer.Lock = True Then
          oLayer.Lock = False
          oBlRef.Layer = pclOptions.psDopSterLayer
          oLayer.Lock = True
        Else
          oBlRef.Layer = pclOptions.psDopSterLayer
        End If
      End If
    Next
  End If
  
Exit Function
HasError:
  Select Case Err.Number
    Case Else
      MsgBox Err.Description, vbCritical, pcsVBProjectName
  End Select
End Function

Public Function ProvKarBlNameAndAtrMarky(sKarBlName As String, sAtrMarky As String) As Boolean
  'проверяем равенство марки каркаса в имени блока и значении атрибута
  'в имени блока допускается в скобках добавлять кол-во плоских каркасов
  'в значении атрибута марки - высоту ростверка
  Dim intValue As String
  
  intValue = InStr(LCase(sKarBlName), "(шт.")
  If intValue <> 0 Then
    sKarBlName = Left(sKarBlName, intValue - 1)
  End If
  
  intValue = InStr(sAtrMarky, "(")
  If intValue <> 0 Then
    sAtrMarky = Left(sAtrMarky, intValue - 1)
  End If
    
  If LCase(sAtrMarky) = LCase(sKarBlName) Then
    ProvKarBlNameAndAtrMarky = True
  Else
    ProvKarBlNameAndAtrMarky = False
  End If
   
End Function

Public Function SortyrBlInColByName(colBl As Collection)
   'сортировка блоков в коллекции, по имени
   
   Dim objBlRefTemp As Object
   Dim i As Integer
   Dim j As Integer
   Dim intCount As Integer
   
   intCount = colBl.Count
   
   For i = 1 To intCount - 1
      For j = 1 To intCount - i
         If StrComp(colBl.Item(j).Name, colBl.Item(j + 1).Name, vbTextCompare) = 1 Then
            Set objBlRefTemp = colBl.Item(j)
            colBl.Remove j
            colBl.Add objBlRefTemp, , , j
         End If
      Next
   Next
   
End Function

Public Function SortyrColProsKarByVal(colBl As Collection)
   'сортировка блоков в коллекции, по кол П
   
   Dim oKar As clKarkas
   Dim i As Integer
   Dim j As Integer
   Dim intCount As Integer
   
   intCount = colBl.Count
   
   If FormSpecRost.CheckBoxMarkaK.Value = False Then
    For i = 1 To intCount - 1
       For j = 1 To intCount - i
          If colBl.Item(j).intP > colBl.Item(j + 1).intP Then
             Set oKar = colBl.Item(j)
             colBl.Remove j
             colBl.Add oKar, oKar.strFirstName, , j
          End If
       Next
    Next
   Else
    For i = 1 To intCount - 1
      For j = 1 To intCount - i
         If colBl.Item(j).intP > colBl.Item(j + 1).intP Then
            Set oKar = colBl.Item(j)
            colBl.Remove j
            colBl.Add oKar, oKar.strFirstName, , j
         ElseIf colBl.Item(j).intP = colBl.Item(j + 1).intP Then
            'сортируем по номеру маркиК плоского каркаса
            If Val(Mid(colBl.Item(j).strMarkaKPlos, 2)) > Val(Mid(colBl.Item(j + 1).strMarkaKPlos, 2)) Then
              Set oKar = colBl.Item(j)
              colBl.Remove j
              colBl.Add oKar, oKar.strFirstName, , j
            End If
         End If
      Next
   Next
   End If
End Function

Public Function SortyrColProsKarByK(colProsKar As Collection)
   'сортировка коллекции простран каркасов, по К и П
   Dim oKar As clKarkas
   Dim i As Integer
   Dim j As Integer
   Dim iNumKj As Integer
   Dim iNumKj1 As Integer
   Dim intCount As Integer
   Dim iTypeJ As Integer
   Dim iTypeJ1 As Integer
   
   intCount = colProsKar.Count
   
    For i = 1 To intCount - 1
      For j = 1 To intCount - i
        'СОРТИРОвка по типу КД,КО,К
        Select Case colProsKar(j).strType
          Case "КД"
            iTypeJ = 1
          Case "КО"
            iTypeJ = 2
          Case "К"
            iTypeJ = 3
        End Select
        Select Case colProsKar(j + 1).strType
          Case "КД"
            iTypeJ1 = 1
          Case "КО"
            iTypeJ1 = 2
          Case "К"
            iTypeJ1 = 3
        End Select
        
        If iTypeJ > iTypeJ1 Then
          Set oKar = colProsKar.Item(j)
          colProsKar.Remove j
          colProsKar.Add oKar, oKar.strFirstName, , j
        ElseIf iTypeJ = iTypeJ1 Then
          'сортируем по номеру маркиК плоского каркаса
          iNumKj = GetNumKFromMarkaK(colProsKar(j).strMarkaK)
          iNumKj1 = GetNumKFromMarkaK(colProsKar(j + 1).strMarkaK)
          If iNumKj > iNumKj1 Then
            Set oKar = colProsKar.Item(j)
            colProsKar.Remove j
            colProsKar.Add oKar, oKar.strFirstName, , j
          ElseIf iNumKj = iNumKj1 Then
            If colProsKar.Item(j).intP > colProsKar.Item(j + 1).intP Then
              Set oKar = colProsKar.Item(j)
              colProsKar.Remove j
              colProsKar.Add oKar, oKar.strFirstName, , j
            End If
          End If
        End If
      Next
   Next
End Function

Public Function SortyrColBlProsKarByK(colBl As Collection)
   'сортировка блоков в коллекции, по кол П
   
   Dim oKar As clKarkas
   Dim i As Integer
   Dim j As Integer
   Dim intCount As Integer
   
   intCount = colBl.Count
   
    For i = 1 To intCount - 1
      For j = 1 To intCount - i
            'сортируем по номеру маркиК плоского каркаса
            If Val(Mid(colBl.Item(j).strMarkaKPlos, 2)) > Val(Mid(colBl.Item(j + 1).strMarkaKPlos, 2)) Then
              Set oKar = colBl.Item(j)
              colBl.Remove j
              colBl.Add oKar, oKar.strFirstName, , j
            ElseIf Val(Mid(colBl.Item(j).strMarkaKPlos, 2)) = Val(Mid(colBl.Item(j + 1).strMarkaKPlos, 2)) Then
              If colBl.Item(j).intP > colBl.Item(j + 1).intP Then
                Set oKar = colBl.Item(j)
                colBl.Remove j
                colBl.Add oKar, oKar.strFirstName, , j
              End If
            End If
      Next
   Next
End Function

Public Function SortyrColPlosKarByVal(colBl As Collection)
   'сортировка блоков в коллекции, по имени
   
   Dim oKar As clKarkas
   Dim i As Integer
   Dim j As Integer
   Dim intCount As Integer
   
   intCount = colBl.Count
   
   For i = 1 To intCount - 1
      For j = 1 To intCount - i
         If colBl.Item(j).intN > colBl.Item(j + 1).intN Then
            Set oKar = colBl.Item(j)
            colBl.Remove j
            colBl.Add oKar, oKar.strPlosKarName, , j
         End If
      Next
   Next
   
End Function

Public Function SortyrColPlosKarByK(colBl As Collection)
   'сортировка блоков в коллекции, по порядку К1, К2 ...
   
   Dim oKar As clKarkas
   Dim oKar1 As clKarkas
   Dim oKar2 As clKarkas
   Dim i As Integer
   Dim j As Integer
   Dim intCount As Integer
   Dim iNumK1 As Integer
   Dim iNumK2 As Integer
   
   intCount = colBl.Count
   For i = 1 To intCount - 1
      For j = 1 To intCount - i
        Set oKar1 = colBl.Item(j)
        Set oKar2 = colBl.Item(j + 1)
        If StrComp(oKar1.strType, oKar2.strType) = 1 Then
          'Set oKar = colBl.Item(j)
          colBl.Remove j
          colBl.Add oKar1, oKar1.strPlosKarName, , j
        ElseIf StrComp(oKar1.strType, oKar2.strType) = 0 Then
          iNumK1 = GetNumKFromMarkaK(oKar1.strMarkaKPlos)
          iNumK2 = GetNumKFromMarkaK(oKar2.strMarkaKPlos)
          If iNumK1 > iNumK2 Then
             colBl.Remove j
             colBl.Add oKar1, oKar1.strPlosKarName, , j
          End If
        End If
      Next
   Next
   
End Function

Public Function GetNumKFromMarkaK(sMarkaK As String) As Integer
  'определение номера из маркиК (8ПК7)
  Dim iVal As Integer
  
  iVal = InStr(sMarkaK, "К")
  If Mid(sMarkaK, iVal + 1, 1) Like "[1-9]" Then
    GetNumKFromMarkaK = Val(Mid(sMarkaK, iVal + 1))
  Else
    GetNumKFromMarkaK = Val(Mid(sMarkaK, iVal + 2))
  End If
  
End Function

Public Function SortyrClDopSterInCol(colClDopSter As Collection)
   'сортировка блоков в коллекции, по имени
   
   Dim oDopSter As clDopStergen
   Dim i As Integer
   Dim j As Integer
   Dim intCount As Integer
   
   intCount = colClDopSter.Count
   
   For i = 1 To intCount - 1
      For j = 1 To intCount - i
         If colClDopSter.Item(j).iDiametr < colClDopSter.Item(j + 1).iDiametr Then
            Set oDopSter = colClDopSter.Item(j)
            colClDopSter.Remove j
            colClDopSter.Add oDopSter, , , j
         ElseIf colClDopSter.Item(j).iDiametr = colClDopSter.Item(j + 1).iDiametr Then
            'сравниваем длину
            If colClDopSter.Item(j).iLenght < colClDopSter.Item(j + 1).iLenght Then
              Set oDopSter = colClDopSter.Item(j)
              colClDopSter.Remove j
              colClDopSter.Add oDopSter, oDopSter.sNaimenovanie, , j
            End If
         End If
      Next
   Next
   
End Function

Public Function GetMacroFolder() As String
   'получение пути к корню макроса
   'без \
   
   Dim intValue As Integer
   
   On Error GoTo HasError
   
   GetMacroFolder = Application.VBE.vbprojects.Item(pcsVBProjectName).FileName
   intValue = InStrRev(GetMacroFolder, "\")
   GetMacroFolder = Left(GetMacroFolder, intValue - 1) 'корень с макросом, без \ на конце
      
Exit Function
HasError:
      MsgBox Err.Description, vbCritical, pcsVBProjectName
End Function

Public Function ProvDublicatov()
  'проверка блоков после ЗБ на наложение по BoundingBox
   
   Dim oEnt As AcadEntity
   Dim objBlockRef As AcadBlockReference
   Dim objBlockRef2 As AcadBlockReference
   Dim oSelSet As AcadSelectionSet
   Dim oSelSet2 As AcadSelectionSet
   Dim intFilterType(1) As Integer
   Dim varFilterDate(1) As Variant
   Dim vMinPt1 As Variant
   Dim vMaxPt1 As Variant
   Dim vMinPt2 As Variant
   Dim vMaxPt2 As Variant
   
   Set pcolBlDublicates = Nothing
   
   Set oSelSet = ThisDrawing.SelectionSets.Item(pcsVBProjectName)
   Set oSelSet2 = Functions.GetSelSet("Вокруг_блока")

   For Each oEnt In oSelSet 'перебор всех объектов набора
    If TypeOf oEnt Is AcadBlockReference Then
      Set objBlockRef = oEnt
      'если блок подпадает под тип для спец-ий
      If InStr(objBlockRef.Name, "К") <> 0 _
        Or InStr(objBlockRef.Name, pclOptions.psSetkaConst) <> 0 Or _
        InStr(objBlockRef.Name, pclOptions.psDopSterConst) <> 0 Then
        'получаем границы первого блока
        objBlockRef.GetBoundingBox vMinPt1, vMaxPt1
              
        'фильтр блока по имени с атрибутом
        intFilterType(0) = 0: intFilterType(1) = 2
        varFilterDate(0) = "insert": varFilterDate(1) = objBlockRef.Name
  
        oSelSet2.Select acSelectionSetCrossing, vMinPt1, vMaxPt1, intFilterType, varFilterDate
              
        For Each objBlockRef2 In oSelSet2 'перебор всех объектов набора
          If Not objBlockRef2 Is objBlockRef Then
            'проверка наложения по границе
            'сравнение точек BoundingBox'оф
            'получаем границы блока
            objBlockRef2.GetBoundingBox vMinPt2, vMaxPt2
            If ProvBoundingBox(vMinPt1, vMinPt2, vMaxPt1, vMaxPt2, pclOptions.pintRadNalog) = True Then
              'заносим блок в колекцию (потенциально) наложенных блоков
              pcolBlDublicates.Add objBlockRef
            End If
          End If 'Id1 <> Id2 Then
        Next 'lCounter = 1 To objSelSet.Count 'перебор всех объектов чертежа
  
        oSelSet2.Clear
        
      End If 'тип блока для спец.
    End If 'TypeOf oEnt Is AcadBlockReference Then
   Next 'oEnt In oSelSet
   
   'если есть дубликаты показываем форму
   If pcolBlDublicates.Count <> 0 Then
      FormaProverky.Show
   End If
   
End Function

Private Function ProvBoundingBox(MinPt1 As Variant, MinPt2 As Variant, MaxPt1 As Variant, MaxPt2 As Variant, Dopusk As Integer) As Boolean
   'проверка наложенитя точек
   'наложение считается совпадение (в допусках) обоих точек BoundingBox
   'True - наложение
   
   'проверяем первую точку
   If MinPt2(0) < MinPt1(0) + Dopusk And MinPt2(0) > MinPt1(0) - Dopusk And _
       MinPt2(1) < MinPt1(1) + Dopusk And MinPt2(1) > MinPt1(1) - Dopusk Then
       'проверяем вторую точку
      If MaxPt2(0) < MaxPt1(0) + Dopusk And MaxPt2(0) > MaxPt1(0) - Dopusk And _
          MaxPt2(1) < MaxPt1(1) + Dopusk And MaxPt2(1) > MaxPt1(1) - Dopusk Then
          'значит точки лежат в пределах наложения, т.е. блоки накладываются
          ProvBoundingBox = True
      Else
         ProvBoundingBox = False
      End If
   Else
      ProvBoundingBox = False
   End If
   
End Function

Public Function ClearSelSets()
  'удаление всех наборов из чертежа
  'CURRENT ???!!!
  'PickFirstSelection ???!!!
  'все равно они же создадутся автоматом потом
  
  Dim selSet As AcadSelectionSet
  Dim i As Integer
  
  For i = 0 To ThisDrawing.SelectionSets.Count - 1
    Set selSet = ThisDrawing.SelectionSets.Item(0)
    selSet.Delete
  Next
  
End Function

Public Function ObrabProsKar()
   'обработка пространственных каркасов из коллекции pcolBlKar
   
  Dim oBlRef As AcadBlockReference
  Dim oClProsKar As clKarkas
  Dim sFirstNameProsKar As String
  Dim i As Integer
  Dim j As Integer
  Dim aiKolP() As Integer
  Dim bolKolP As Boolean
  Dim intUboundKolp As Integer
  
  On Error Resume Next
  
'  MsgBox "Сейчас будут обработаны выбранные блоки каркасов. " & _
'    "Будьте внимательны. При внесении изменений в чертеж - " & _
'    "Рекомендуется повторить Выбор." & _
'    "И не забывайте нажимать кнопку Применить после изменения параметров для выбранного каркаса.", vbInformation, pcsVBProjectName

  'очищаем коллекцию
  Set pcolClProsKar = Nothing
  
  'создание коллекции объектов Каркасов
  For Each oBlRef In pcolBlKar
    'здесь могут оказаться удаленные блоки их пропускаем
    If InStr(oBlRef.Name, "П") <> 0 Then
      If Err Then 'блок удален
        Err.Clear
        GoTo NextBl
      End If
      sFirstNameProsKar = GetFirstNameKar(oBlRef)
      Set oClProsKar = pcolClProsKar.Item(sFirstNameProsKar)
      If Err Then
        Err.Clear
        Set oClProsKar = New clKarkas
        'если расчет с учетом МаркиК
        If FormSpecRost.CheckBoxMarkaK.Value = True Then
          oClProsKar.strMarkaK = GetMarkaKFromBlock(oBlRef)
        End If
        oClProsKar.ObrabName sFirstNameProsKar
        pcolClProsKar.Add oClProsKar, sFirstNameProsKar
      Else
        oClProsKar.intKolKar = oClProsKar.intKolKar + 1
      End If
    End If
NextBl:
  Next
  
  On Error GoTo 0
  
  'проверка порядеовых номеров маркиК
  If FormSpecRost.CheckBoxMarkaK.Value = True Then
    Dim sError As String
    sError = ProvMarokKInColKar(pcolClProsKar)
    If sError <> "" Then
      MsgBox sError, vbCritical, pcsVBProjectName
      Exit Function
    End If
  End If
  
  'заполняем фильтр простр каркасов по кол-ву П
  FormSpecRost.ComboBoxFilterProsKar.Clear
  FormSpecRost.ComboBoxFilterProsKar.AddItem "Все"
  For Each oClProsKar In pcolClProsKar
    bolKolP = False
    For i = 0 To FormSpecRost.ComboBoxFilterProsKar.ListCount - 1
      If Val(FormSpecRost.ComboBoxFilterProsKar.List(i)) = oClProsKar.intP Then
        bolKolP = True
      End If
    Next
    If bolKolP = False Then
      FormSpecRost.ComboBoxFilterProsKar.AddItem oClProsKar.intP & "П"
    End If
  Next
  FormSpecRost.ComboBoxFilterProsKar.AddItem "Необработанные"
  
  'сортировка по кол-ву П
  If FormSpecRost.CheckBoxMarkaK.Value = False Then
    SortyrColProsKarByVal pcolClProsKar
  Else
    SortyrColBlProsKarByK pcolClProsKar
  End If
  
  'если есть загруженные каркасы, применяем их
  If pcolLoadedProsKar.Count <> 0 Then
    PrimLoadedProsKar
  Else
    'заполняем листвиевер простр.каркасов
    ZapListViewProsKar
  End If
  
  'Change номер сечения
  FormSpecRost.TextBoxNSech = 1
  
  'т.е. пока не будет сделан новый выбор, обработка не будет повторятся
  pbolObrabProsKar = True
  
Exit Function
HasError:
  Select Case Err.Number
    Case 5 '"Invalid procedure call or argument"
      Resume Next
    Case -2145386420 'объект был стерт
      GoTo NextBl
    Case Else
      MsgBox Err.Description
  End Select
End Function

Public Function GetMassaDiamPM(intDiam As Integer) As Double
'определение массы 1м.п. арматуры

   Select Case intDiam
      Case 6
         GetMassaDiamPM = 0.222
      Case 8
         GetMassaDiamPM = 0.395
      Case 10
         GetMassaDiamPM = 0.617
      Case 12
         GetMassaDiamPM = 0.888
      Case 14
         GetMassaDiamPM = 1.21
      Case 16
         GetMassaDiamPM = 1.58
      Case 18
         GetMassaDiamPM = 2#
      Case 20
         GetMassaDiamPM = 2.47
      Case 22
         GetMassaDiamPM = 2.98
      Case 25
         GetMassaDiamPM = 3.85
      Case 28
         GetMassaDiamPM = 4.83
      Case 32
         GetMassaDiamPM = 6.31
      Case 36
         GetMassaDiamPM = 7.99
      Case 40
         GetMassaDiamPM = 9.87
   End Select
   
End Function

Public Function GetFirstNameKar(oBlRef As AcadBlockReference) As String
  'имя каркаса, все что после "-" в нижнем регистре
  Dim intValue As Integer
  Dim sMarka As String
  Dim vAtr As Variant
  
  For Each vAtr In oBlRef.GetAttributes
    If vAtr.Layer = pclOptions.psKarAtrMarkaLayer Then
      sMarka = vAtr.TextString
      Exit For
    End If
  Next
  
  intValue = InStr(sMarka, "-")
   'оставшаяся строка до "-"
   If intValue = 0 Then
     GetFirstNameKar = UCase(sMarka)
   Else
   'переводим все что после "-" в нижний регистр
      GetFirstNameKar = UCase(Left(sMarka, intValue)) & LCase(Mid(sMarka, intValue + 1))
   End If

End Function

Public Function GetFirstNamePlosKar(BlName As String) As String
  'имя плоского каркаса, все что после "-" в нижнем регистре, без (шт.2)
  
  Dim intValue As Integer
  Dim strValue As String
  
  intValue = InStr(BlName, "-")
   'оставшаяся строка до "-"
  If intValue = 0 Then
     GetFirstNamePlosKar = BlName
  Else
    'переводим все что после "-" в нижний регистр
    strValue = LCase(Mid(BlName, intValue + 1))
    'имя до "-"
    GetFirstNamePlosKar = UCase(Left(BlName, intValue))
    'полное имя каркаса
    GetFirstNamePlosKar = GetFirstNamePlosKar & strValue
  End If
  
  intValue = InStr(LCase(BlName), "(шт.")
  If intValue <> 0 Then
    'отбрасываем то что в скобках
    GetFirstNamePlosKar = (Left(BlName, intValue - 1))
  End If
End Function

Public Function GetKolShtukPlosKar(BlName As String) As Integer
  'определяем кол-во штук плоских каркасов в блоке (шт.2)
  
  Dim intValue As Integer
  Dim dValue As Double
  
  intValue = InStr(LCase(BlName), "(шт.")
  If intValue = 0 Then
    GetKolShtukPlosKar = 1
  Else
    dValue = Val(Mid(BlName, intValue + 4))
    intValue = dValue
    If intValue <> dValue Then
      'ошибка определения кол-ва плоских каркасов
      GetKolShtukPlosKar = 0
    Else
      GetKolShtukPlosKar = intValue
    End If
  End If
End Function

Public Function ItemProsKarClick(sItemName As String)
  'заполняем данные объекта каркаса в форму вкладка пространств.каркасов
  
  Dim oClProsKar As clKarkas
  
  FormSpecRost.LabelCurProsKarkas = sItemName
  
  'получаем объект из коллекции по ключевому именир
  Set oClProsKar = pcolClProsKar.Item(sItemName)
  
  If oClProsKar.strError = "" Then
    FormSpecRost.cmbPrimProsKar.Enabled = True
  Else
    MsgBox "При обработке имени каркаса найдены ошибки." & vbCr & _
      "Имя каркаса - " & sItemName & vbCr & _
      oClProsKar.strError, vbCritical, pcsVBProjectName
    FormSpecRost.cmbPrimProsKar.Enabled = False
    Exit Function
  End If
  
  'если уже обработан каркас считываем параметры с него
  If oClProsKar.bolObrabotan = True Then
    'заполняем поля формы из объекта
    FormSpecRost.TextBoxNSech = oClProsKar.sNSech
    FormSpecRost.TextBoxLenSech = oClProsKar.intLenSech
'Изменения 17/08/09
    FormSpecRost.TextBoxHeightRost = oClProsKar.intHeightRost
'конец изменений
    'шаг доп.поп.стержень ("-д")
    FormSpecRost.TextBoxShagDopPopSter = oClProsKar.intShagDopPopSter
    FormSpecRost.TextBoxShagNizSvyzSter = oClProsKar.intShagSvyzNizArm
    FormSpecRost.TextBoxShagVerhSvyzSter = oClProsKar.intShagSvyzVerhArm
    FormSpecRost.TextBoxDiamNizSvyzSter = oClProsKar.intDiamSvyzNizArm
    FormSpecRost.TextBoxDiamVerhSvyzSter = oClProsKar.intDiamSvyzVerhArm
    FormSpecRost.TextBoxNizZachBet = oClProsKar.intCenterNizArm
    FormSpecRost.TextBoxVerhZachBet = oClProsKar.intCenterVerhArm
    'усиление если есть
    If oClProsKar.bolUsilenie = False Then
      FormSpecRost.CheckBoxUsilenie.Value = False
'      FormSpecRost.FrameUsilenie.Enabled = False
'      FormSpecRost.TextBoxUsLenSech.Enabled = False
'      FormSpecRost.TextBoxUsDiamNizArm.Enabled = False
'      FormSpecRost.TextBoxUsDiamVerhArm.Enabled = False
'      FormSpecRost.TextBoxUsShagNizArm.Enabled = False
'      FormSpecRost.TextBoxUsShagVerhArm.Enabled = False
'      FormSpecRost.TextBoxUsKlassNizArm.Enabled = False
'      FormSpecRost.TextBoxUsKlassVerhArm.Enabled = False
'      FormSpecRost.TextBoxUsGOSTNizArm.Enabled = False
'      FormSpecRost.TextBoxUsGOSTVerhArm.Enabled = False
    Else
      FormSpecRost.CheckBoxUsilenie.Value = True
'      FormSpecRost.FrameUsilenie.Enabled = True
'      FormSpecRost.CheckBoxUsilenie.Value = True
'      FormSpecRost.FrameUsilenie.Enabled = True
'      FormSpecRost.TextBoxUsLenSech.Enabled = True
'      FormSpecRost.TextBoxUsDiamNizArm.Enabled = True
'      FormSpecRost.TextBoxUsDiamVerhArm.Enabled = True
'      FormSpecRost.TextBoxUsShagNizArm.Enabled = True
'      FormSpecRost.TextBoxUsShagVerhArm.Enabled = True
'      FormSpecRost.TextBoxUsKlassNizArm.Enabled = True
'      FormSpecRost.TextBoxUsKlassVerhArm.Enabled = True
'      FormSpecRost.TextBoxUsGOSTNizArm.Enabled = True
'      FormSpecRost.TextBoxUsGOSTVerhArm.Enabled = True
      FormSpecRost.TextBoxUsLenSech = oClProsKar.intUsLen
      FormSpecRost.TextBoxUsKolSech = oClProsKar.intUsKolKar
      FormSpecRost.TextBoxUsDiamNizArm = oClProsKar.intUsDiamNizArm
      FormSpecRost.TextBoxUsDiamVerhArm = oClProsKar.intUsDiamVerhArm
      FormSpecRost.TextBoxUsShagNizArm = oClProsKar.intUsShagNizArm
      FormSpecRost.TextBoxUsShagNizArm = oClProsKar.intUsShagNizArm
      FormSpecRost.TextBoxUsKlassNizArm = oClProsKar.sUsKlassNizArm
      FormSpecRost.TextBoxUsKlassVerhArm = oClProsKar.sUsKlassVerhArm
      FormSpecRost.TextBoxUsGOSTNizArm = oClProsKar.sUsGOSTNizArm
      FormSpecRost.TextBoxUsGOSTVerhArm = oClProsKar.sUsGOSTVerhArm
    End If
    FormSpecRost.TextBoxKlassVerhArm = oClProsKar.sKlassVerhArm
    FormSpecRost.TextBoxKlassNizArm = oClProsKar.sKlassNizArm
    FormSpecRost.TextBoxKlassPopArm = oClProsKar.sKlassPopArm
    FormSpecRost.TextBoxKlassSvyzNizArm = oClProsKar.sKlassSvyzNizArm
    FormSpecRost.TextBoxKlassSvyzVerhArm = oClProsKar.sKlassSvyzVerhArm
    FormSpecRost.TextBoxGOSTNizArm = oClProsKar.sGOSTNizArm
    FormSpecRost.TextBoxGOSTVerhArm = oClProsKar.sGOSTVerhArm
    FormSpecRost.TextBoxGOSTPopArm = oClProsKar.sGOSTPopArm
    FormSpecRost.TextBoxGOSTSvyzNizArm = oClProsKar.sGOSTSvyzNizArm
    FormSpecRost.TextBoxGOSTSvyzVerhArm = oClProsKar.sGOSTSvyzVerhArm
    
  Else 'oClProsKar.bolObrabotan = True
  
    'сечение по умолчанию
    'FormSpecRost.TextBoxNSech = "1"

    'считываем значения по-умолчанию с настроек
    'заполняем поля формы
    '******* изменения 12.11.09 созранять параметры сечения только для панелек (для кирпички не нужно)
'    If FormSpecRost.CheckBoxMarkaK.Value = True Then
'       pclOptions.LoadProsKarParamSech
'    End If
    'шаг доп.поп.стержень ("-д")
    FormSpecRost.TextBoxShagDopPopSter = oClProsKar.intShagDopPopSter ' pclOptions.piShagDopPopSterDef
    
  End If 'oClProsKar.bolObrabotan = False Then
  
  'если есть доп.поп.стержень ("-д")
  If oClProsKar.bolD = False Then
    FormSpecRost.TextBoxShagDopPopSter.Enabled = False
  Else
    FormSpecRost.TextBoxShagDopPopSter.Enabled = True
  End If
  
  'если высота ростверка задана в имени каркаса (в скобках - "(6)")
  If oClProsKar.bolHeightRostInName = False Then
    FormSpecRost.TextBoxHeightRost.Locked = False
    FormSpecRost.TextBoxHeightRost.Enabled = True
  Else
    FormSpecRost.TextBoxHeightRost.Locked = True 'блокируем поле
    FormSpecRost.TextBoxHeightRost.Enabled = False
    FormSpecRost.TextBoxHeightRost = oClProsKar.intHeightRost
  End If
  
End Function

Public Function ItemPlosKarClick(sItemName As String)
  'заполняем данные объекта каркаса в форму вкладка плос.каркасов
  
  Dim oClPlosKar As clKarkas
  
  'получаем объект из коллекции по ключевому имени
  Set oClPlosKar = pcolClPlosKar.Item(sItemName)
  
  If oClPlosKar.strError = "" Then
    FormSpecRost.cmbPrimPlosKar.Enabled = True
  Else
    MsgBox "При обработке имени каркаса найдены ошибки." & vbCr & _
      "Имя каркаса - " & sItemName & vbCr & _
      oClPlosKar.strError, vbCritical, pcsVBProjectName
    FormSpecRost.cmbPrimPlosKar.Enabled = False
    Exit Function
  End If
  
  'очищаем листвиевер сечений плоских каркасов
  FormSpecRost.ListViewPlosKarSech.ListItems.Clear
  
  'если каркас уже был обработан считываем параметры с него
  If oClPlosKar.bolObrabotan = True Then
    'заполняем поля формы из объекта
    FormSpecRost.TextBoxHPlosKar = oClPlosKar.intHeightRost
    FormSpecRost.TextBoxZachVerhPlosKar = oClPlosKar.intCenterVerhArm
    FormSpecRost.TextBoxZachNizPlosKar = oClPlosKar.intCenterNizArm
    FormSpecRost.TextBoxKlassVerhPlosKar = oClPlosKar.sKlassVerhArm
    FormSpecRost.TextBoxKlassNizPlosKar = oClPlosKar.sKlassNizArm
    FormSpecRost.TextBoxKlassPopPlosKar = oClPlosKar.sKlassPopArm
    FormSpecRost.TextBoxGOSTVerhPlosKar = oClPlosKar.sGOSTVerhArm
    FormSpecRost.TextBoxGOSTNizPlosKar = oClPlosKar.sGOSTNizArm
    FormSpecRost.TextBoxGOSTPopPlosKar = oClPlosKar.sGOSTPopArm
    'если есть доп.поп.стержень ("-д")
    FormSpecRost.TextBoxShagDopPopPlosKar = oClPlosKar.intShagDopPopSter
    
    'считываем параметры сечений плоского каркаса
    Dim oPlosKarSech As clPlosKarSech
    Set oPlosKarSech = pcolClPlosKarSech.Item(sItemName)
    'вывод параметров сечений в листвиевер сечений
    oPlosKarSech.GetParamSech
    
  Else
    'считываем значения по-умолчанию с настроек
    'заполняем поля формы
    FormSpecRost.TextBoxHPlosKar = pclOptions.iHeightRostDef
    FormSpecRost.TextBoxZachVerhPlosKar = pclOptions.iZachBetVerhDef
    FormSpecRost.TextBoxZachNizPlosKar = pclOptions.iZachBetNizDef
    FormSpecRost.TextBoxKlassVerhPlosKar = pclOptions.psKlassVerhDef
    FormSpecRost.TextBoxKlassNizPlosKar = pclOptions.psKlassNizDef
    FormSpecRost.TextBoxKlassPopPlosKar = pclOptions.psKlassPopDef
    FormSpecRost.TextBoxGOSTVerhPlosKar = pclOptions.psGOSTVerhDef
    FormSpecRost.TextBoxGOSTNizPlosKar = pclOptions.psGOSTNizDef
    FormSpecRost.TextBoxGOSTPopPlosKar = pclOptions.psGOSTPopDef
    'если есть доп.поп.стержень ("-д")
    FormSpecRost.TextBoxShagDopPopPlosKar = oClPlosKar.intShagDopPopSter ' pclOptions.piShagDopPopSterDef
  End If 'oClProsKar.bolObrabotan = False Then
  
  'если есть доп.поп.стержень ("-д")
  If oClPlosKar.bolD = False Then
    FormSpecRost.TextBoxShagDopPopPlosKar.Enabled = False
  Else
    FormSpecRost.TextBoxShagDopPopPlosKar.Enabled = True
  End If
  
  'если высота ростверка задана в имени каркаса (в скобках - "(6)")
  If oClPlosKar.bolHeightRostInName = False Then
    FormSpecRost.TextBoxHPlosKar.Locked = False
  Else
    FormSpecRost.TextBoxHPlosKar.Locked = True 'блокируем поле
    FormSpecRost.TextBoxHPlosKar = oClPlosKar.intHeightRost
  End If
  
End Function

Public Function GetShifrFromDict() As String
   'чтение записи шифра из словаря
   'словарь SPD
   'запись Shifr
   'если нет словаря или записи, возвращает ""
   
   Dim objDict As AcadDictionary
   Dim objXRec As AcadXRecord
   Dim XRDataType As Variant
   Dim XRDataValue As Variant
   
   On Error GoTo HasError
   
   'получаем словарь чертежа
   Set objDict = pdocSpecRost.Dictionaries.Item("SPD")
   'получаем запись SPD из словаря
   Set objXRec = objDict.Item("Shifr")
   'считываем данные записи
   objXRec.GetXRecordData XRDataType, XRDataValue
   
   If IsEmpty(XRDataValue) = True Then
      GetShifrFromDict = ""
      Exit Function
   Else
      GetShifrFromDict = XRDataValue(0)
      Exit Function
   End If

Exit Function
HasError:
   Select Case Err.Number
      Case -2145386476 'Ключ не найден
         'если нет записи
         'возвращаем пустую строчку
'         MsgBox "Ключ не найден"
         GetShifrFromDict = ""
         Exit Function
      Case Else
         MsgBox "Функция GetShifrFromDict - " & Err.Description
         GetShifrFromDict = ""
         Exit Function
   End Select
End Function

Public Function ObrabAttributov()
  'обработка исх.данных проекта
  'считываем шифр из словаря
  'считываем данные шифра из каталога шифров
  'заполняем вкладку Исх.Данные
  
  Dim sShifr As String
  
  'если не определен чертеж для расчетов то и делать нечего
  If pdocSpecRost Is Nothing Then
    MsgBox "С начало нужно выбрать блоки на чертеже." & vbCr & _
      "Перейдите на вкладку Выбор.", vbInformation, pcsVBProjectName
      Exit Function
  End If
  
  'считываем шифр чертежа из его словаря
  sShifr = Functions.GetShifrFromDict
  If sShifr = "" Then
    MsgBox "Шифр не назначен. " & _
      "Рекомендуется, скрыть эту форму, назначить чертежу шифр из каталога шифров, потом продолжить расчет.", vbInformation, pcsVBProjectName
      Exit Function
  End If
  
  'получаем объект шифра по данным из базы
  
  Set oShifr = Functions.GetObjShifr(sShifr)
  'если объект шифра получен
  If oShifr Is Nothing Then
    MsgBox "Шифр определен - " & sShifr & ", но не найден в каталоге шифров. " & _
      "Рекомендуется скрыть эту форму, добавить данные шифра в каталог шифров, потом продолжить.", vbInformation, pcsVBProjectName
  Else
    'If MsgBox("Заполнить исходные данные из каталога шифров, для шифра - " & sShifr, vbYesNo + vbQuestion, pcsVBProjectName) = vbYes Then
      'заполняем данные из шифра
      FormSpecRost.TextBoxShifr = oShifr.Shifr & "-" & oShifr.Part
      FormSpecRost.TextBoxAdres = oShifr.Adress
      FormSpecRost.TextBoxNaimenDoma = oShifr.ObjectName
      FormSpecRost.TextBoxPost1 = oShifr.Post1
      FormSpecRost.TextBoxPost2 = oShifr.Post2
      FormSpecRost.TextBoxPost3 = oShifr.Post3
      FormSpecRost.TextBoxPost4 = oShifr.Post4
      FormSpecRost.TextBoxFam1 = oShifr.Fam1
      FormSpecRost.TextBoxFam2 = oShifr.Fam2
      FormSpecRost.TextBoxFam3 = oShifr.Fam3
      FormSpecRost.TextBoxFam4 = oShifr.Fam4
      
    'End If
    
    'если есть (б.с.)
    If oShifr.BS <> "" Then
      FormSpecRost.CheckBoxShifrBS.Visible = True
    Else
      FormSpecRost.CheckBoxShifrBS.Visible = False
    End If
    
  End If
  
End Function

Public Function ObrabPlosKar()
  'обработка выбранных блоков плоских каркасов
  'обработка пространственных каркасов из коллекции pcolBlKar
   
  Dim oBlRef As AcadBlockReference
  Dim oClPlosKar As clKarkas
  Dim oClPlosKarSech As clPlosKarSech
  Dim oListItem As ListItem
  Dim sFirstNamePlosKar As String
  Dim i As Integer
  Dim j As Integer
  Dim aiKolP() As Integer
  Dim bolKolP As Boolean
  Dim intUboundKolp As Integer
  Dim intKolShtuk As Integer
  Dim bolMarkaK As Boolean
  
  On Error Resume Next
  
  'очищаем коллекцию
  Set pcolClPlosKar = Nothing
  Set pcolClPlosKarSech = Nothing
  
  bolMarkaK = FormSpecRost.CheckBoxMarkaK.Value
  
  'создание коллекции объектов Каркасов
  For Each oBlRef In pcolBlKar
    'здесь могут оказаться удаленные блоки их пропускаем
    If InStr(oBlRef.Name, "П") = 0 Then
      If Err Then 'блок удален
        Err.Clear
        GoTo NextBl
      End If
      sFirstNamePlosKar = GetFirstNameKar(oBlRef)
      intKolShtuk = GetKolShtukPlosKar(oBlRef.Name)
      Set oClPlosKar = pcolClPlosKar.Item(sFirstNamePlosKar)
      If Err Then
        Err.Clear
        Set oClPlosKar = New clKarkas
        If bolMarkaK = True Then
          oClPlosKar.strMarkaK = GetMarkaKFromBlock(oBlRef)
        End If
        oClPlosKar.ObrabName sFirstNamePlosKar
        If intKolShtuk = 0 Then
          oClPlosKar.strError = oClPlosKar.strError & vbCr & "Кол-во каркасов неопределено (шт.?)"
        End If
        oClPlosKar.intKolKar = intKolShtuk
        pcolClPlosKar.Add oClPlosKar, sFirstNamePlosKar
        'создаем объект параметров сечений плоского каркаса и заносим в коллекцию
        Set oClPlosKarSech = New clPlosKarSech
        
        'Изменения 07,04,10 !!!!!!!!!??????????
        Set oClPlosKarSech.poPlosKar = oClPlosKar
        
        oClPlosKarSech.sMarkaPlosKar = sFirstNamePlosKar
        pcolClPlosKarSech.Add oClPlosKarSech, sFirstNamePlosKar
      Else
        oClPlosKar.intKolKar = oClPlosKar.intKolKar + intKolShtuk
      End If
    End If
NextBl:
  Next
  
  On Error GoTo 0
  
  'проверка порядеовых номеров маркиК
  If FormSpecRost.CheckBoxMarkaK.Value = True Then
    Dim sError As String
    sError = ProvMarokKInColKar(pcolClPlosKar)
    If sError <> "" Then
      MsgBox sError, vbCritical, pcsVBProjectName
      Exit Function
    End If
  End If
  
  'если есть загруженные каркасы, применяем их
  If pcolLoadedPlosKar.Count <> 0 Then
    PrimLoadedPlosKar
  Else
    'заполняем листвиевер плоских.каркасов
    FormSpecRost.ListViewPlosKar.ListItems.Clear
    For Each oClPlosKar In pcolClPlosKar
      'если при обработке имени каркаса возникли ошибки то ставим крест
      If oClPlosKar.strError = "" Then
        If oClPlosKar.bolObrabotan = True Then
          Set oListItem = FormSpecRost.ListViewPlosKar.ListItems.Add(, , oClPlosKar.strFirstName, , 1)
        Else
          Set oListItem = FormSpecRost.ListViewPlosKar.ListItems.Add(, , oClPlosKar.strFirstName)
        End If
      Else
        Set oListItem = FormSpecRost.ListViewPlosKar.ListItems.Add(, , oClPlosKar.strFirstName, , 2)
      End If
      oListItem.SubItems(1) = oClPlosKar.intKolKar
      oListItem.SubItems(2) = oClPlosKar.strMarkaKPlos
    Next
  End If
  
  'заполняем параметры простр.каркаса по-умолчанию
  pclOptions.LoadPlosKarParamProsSechDef
  
  'т.е. пока не будет сделан новый выбор, обработка не будет повторятся
  pbolObrabPlosKar = True
  
Exit Function
HasError:
  Select Case Err.Number
    Case 5 '"Invalid procedure call or argument"
      Resume Next
    Case -2145386420 'объект был стерт
      GoTo NextBl
    Case Else
      MsgBox Err.Description
  End Select
End Function

Public Function ObrabSetok()
  'обработка выбранных блоков сеток
  Dim oBlRef As AcadBlockReference
  Dim oSetka As clSetky
  Dim oListItem As ListItem
  Dim i As Integer
  Dim j As Integer
  Dim sBlName As String
  
  On Error Resume Next
  
  'очищаем коллекцию
  Set pcolClSetky = Nothing
  
  'создание коллекции объектов сеток
  For Each oBlRef In pcolBlSetky
    'здесь могут оказаться удаленные блоки их пропускаем
    sBlName = oBlRef.Name
      If Err Then 'блок удален
        Err.Clear
        GoTo NextBl
      End If
      'если уже есть такой сетка в коллекции
      Set oSetka = pcolClSetky.Item(sBlName)
      If Err Then
        'если нет добавляем новый
        Err.Clear
        Set oSetka = New clSetky
        oSetka.ObrabBlName sBlName
        oSetka.piKolvoBl = 1
        oSetka.piKolSetok = oSetka.piKolShtuk
        pcolClSetky.Add oSetka, sBlName
      Else
        'если есть, добавляем кол-во
        oSetka.piKolvoBl = oSetka.piKolvoBl + 1
        oSetka.piKolSetok = oSetka.piKolSetok + oSetka.piKolShtuk
      End If
NextBl:
  Next
  
  On Error GoTo 0
  
  'если есть загруженные сетки, применяем их
  If pcolLoadedSetky.Count <> 0 Then
    PrimLoadedSetky
  Else
    'заполняем листвиевер сеток
    FormSpecRost.ListViewSetky.ListItems.Clear
    For Each oSetka In pcolClSetky
      'если при обработке имени возникли ошибки то ставим крест
      If oSetka.psError = "" Then
        Set oListItem = FormSpecRost.ListViewSetky.ListItems.Add(, , oSetka.psBlName)
      Else
        Set oListItem = FormSpecRost.ListViewSetky.ListItems.Add(, , oSetka.psBlName, , 2)
      End If
      oListItem.ListSubItems.Add , , oSetka.piKolvoBl
    Next
  End If
  
  'т.е. пока не будет сделан новый выбор, обработка не будет повторятся
  pbolObrabSetok = True
  
End Function

Public Function ObrabDopSter()
  'обработка выбранных блоков доп.стержней
  
  Dim oBlRef As AcadBlockReference
  Dim oDopSter As clDopStergen
  Dim oDopSterTemp As clDopStergen
  Dim oListItem As ListItem
  Dim i As Integer
  Dim j As Integer
  Dim sBlName As String
  
  On Error Resume Next
  
  'очищаем коллекцию
  Set pcolClDopStergny = Nothing
  
  'создание коллекции объектов доп.стержней
  For Each oBlRef In pcolBlDopSterg
    'здесь могут оказаться удаленные блоки их пропускаем
    sBlName = oBlRef.Name
      If Err Then 'блок удален
        Err.Clear
        GoTo NextBl
      End If
      Set oDopSterTemp = New clDopStergen
      'определяем наименование доп.стержня "18-A-III ГОСТ 8781-82, L=2000"
      oDopSterTemp.ObrabBlName sBlName
      oDopSterTemp.iKolvo = oDopSterTemp.iKolShtuk
      'если уже есть такой стержень в коллекции доп.стержней
      Set oDopSter = pcolClDopStergny.Item(oDopSterTemp.sNaimenovanie)
      If Err Then
        'если нет добавляем новый
        Err.Clear
        pcolClDopStergny.Add oDopSterTemp, oDopSterTemp.sNaimenovanie
      Else
        'если есть, добавляем кол-во
        oDopSter.iKolvo = oDopSter.iKolvo + oDopSterTemp.iKolvo
      End If
NextBl:
  Next
  
  On Error GoTo 0
  
  'сортировка доп.стержней по диаметру и длине стержня
  Functions.SortyrClDopSterInCol pcolClDopStergny
  
  'если есть загруженные стержней, применяем их
  If pcolLoadedDopSterg.Count <> 0 Then
    PrimLoadedDopStergny
  Else
    'заполняем листвиевер доп.стержней
    FormSpecRost.ListViewDopSter.ListItems.Clear
    For Each oDopSter In pcolClDopStergny
      'если при обработке имени доп.стержня возникли ошибки то ставим крест
      If oDopSter.sError = "" Then
        Set oListItem = FormSpecRost.ListViewDopSter.ListItems.Add(, , oDopSter.sNaimenovanie)
      Else
        Set oListItem = FormSpecRost.ListViewDopSter.ListItems.Add(, , oDopSter.sNaimenovanie, , 2)
      End If
      oListItem.ListSubItems.Add , , oDopSter.iKolvo
    Next
  End If
  
  'т.е. пока не будет сделан новый выбор, обработка не будет повторятся
  pbolObraDopSter = True
  
Exit Function
HasError:
  Select Case Err.Number
    Case 5 '"Invalid procedure call or argument"
      Resume Next
    Case -2145386420 'объект был стерт
      GoTo NextBl
    Case Else
      MsgBox Err.Description
  End Select
End Function

Public Function ObrabPerepadov()
  'обработка перепадов чертежа
End Function

Public Function ObrabSpec()
  'подготовка с расчету
  'определение замечаний
  'и возможностии сделать расчет спецификаций
  
  Dim oKar As clKarkas
  Dim oSechPlosKar As clPlosKarSech
  Dim sErrorList As String
  
  'выбраны ли блоки
  If pcolBlKar.Count = 0 And pcolBlSetky.Count = 0 And pcolBlDopSterg.Count = 0 Then
    sErrorList = sErrorList & "Нет выбранных блоков для расчета" & vbCrLf
  Else
    'сохранен ли чертеж ена диске
    If pdocSpecRost.FullName = "" Then
      sErrorList = sErrorList & "Сохраните чертеж на диске" & vbCrLf
    End If
    
    'заполнены ли исх.данные
    If FormSpecRost.TextBoxShifr = "" Then
      sErrorList = sErrorList & "Не заполнен шифр в исходных данных" & vbCrLf
    End If
  End If
  
  'проверяем все ли простр каркасы обработаны
  If pbolObrabProsKar = False Then
    sErrorList = sErrorList & "Не обработаны простр.каркасы. Перейдите на вкладку Простр.кар" & vbCrLf
  Else
    For Each oKar In pcolClProsKar
      If oKar.bolObrabotan = False Then
        sErrorList = sErrorList & "Не всем простр.каркасам назначены параметры!" & vbCrLf
        Exit For
      End If
      If oKar.strError <> "" Then
        sErrorList = sErrorList & "Есть ошибки в параметрах пространственных каркасов!" & vbCrLf
        Exit For
      End If
    Next
  End If
  
  'проверяем все ли плоские каркасы обработаны
  If pbolObrabPlosKar = False Then
    sErrorList = sErrorList & "Не обработаны плоские каркасы. Перейдите на вкладку Плоских каркасов" & vbCrLf
  Else
    For Each oKar In pcolClPlosKar
      If oKar.bolObrabotan = False Then
        sErrorList = sErrorList & "Не всем плоским каркасам назначены параметры!" & vbCrLf
        Exit For
      End If
      If oKar.strError <> "" Then
        sErrorList = sErrorList & "Есть ошибки в параметрах плоских каркасов!" & vbCrLf
        Exit For
      End If
    Next
  End If
  'проверяем все ли сечения плоских каркасов обработаны
  For Each oSechPlosKar In pcolClPlosKarSech
    If oSechPlosKar.ProvKolSech = False Then
      sErrorList = sErrorList & "Не все плоские каркасам распределены по сечениям!" & vbCrLf
      Exit For
    End If
  Next
  
  'Кнопка для вывода имен плоских каркасов для выбранного сечения
  FormSpecRost.cmbViewKarForSech.Enabled = True
  
  'проверяем все ли сетки обработаны
  If pcolBlSetky.Count <> 0 Then
    If pbolObrabSetok = False Then
      sErrorList = sErrorList & _
        "Сетки не обработаны. Перейдите на вкладку сеток." & vbCrLf
    Else
      Dim oSetka As clSetky
      For Each oSetka In pcolClSetky
        If oSetka.pbObrab = False Then
          sErrorList = sErrorList & "Не всем сеткам назначены параметры!" & vbCrLf
          Exit For
        End If
      Next
    End If
  End If
  
  'проверяем все ли доп.стержни обработаны
  If pcolClDopStergny.Count <> 0 Then
    If pbolObraDopSter = False Then
      sErrorList = sErrorList & _
        "Доп.стержни не обработаны. Перейдите на вкладку доп.стержней." & vbCrLf
      Dim oDopSter As clDopStergen
      For Each oDopSter In pcolClDopStergny
        If oDopSter.iPoz = 0 Then
          sErrorList = sErrorList & "Не всем доп.стержням назначена позиция!" & vbCrLf
          Exit For
        End If
      Next
    End If
  End If
  
  'проверяем определены ли перепады
  If pbolObrabPerepadov = False Then
    sErrorList = sErrorList & _
      "Не определены перепады отметки ростверка по высоте!" & vbCrLf
  End If
  
  If sErrorList = "" Then
    FormSpecRost.TextBoxError = "ok"
  Else
    FormSpecRost.TextBoxError = sErrorList
  End If
  
End Function

Public Function ProvDiamStandard(Diam As Integer) As Boolean
   Select Case Diam
      Case 6
         ProvDiamStandard = True
      Case 8
         ProvDiamStandard = True
      Case 10
         ProvDiamStandard = True
      Case 12
         ProvDiamStandard = True
      Case 14
         ProvDiamStandard = True
      Case 16
         ProvDiamStandard = True
      Case 18
         ProvDiamStandard = True
      Case 20
         ProvDiamStandard = True
      Case 22
         ProvDiamStandard = True
      Case 25
         ProvDiamStandard = True
      Case 28
         ProvDiamStandard = True
      Case 32
         ProvDiamStandard = True
      Case 36
         ProvDiamStandard = True
      Case 40
         ProvDiamStandard = True
      Case Else
         ProvDiamStandard = False
   End Select
   
End Function

Public Function SetParamProsKar(oClProsKar As clKarkas)
  'установка параметров с формы для пространственного каркаса
    
  oClProsKar.sNSech = FormSpecRost.TextBoxNSech
  oClProsKar.intLenSech = FormSpecRost.TextBoxLenSech
  'если высота ростверка задана в имени каркаса (в скобках - "(6)")
  If oClProsKar.bolHeightRostInName = False Then
    oClProsKar.intHeightRost = FormSpecRost.TextBoxHeightRost
  End If
  oClProsKar.intShagSvyzNizArm = FormSpecRost.TextBoxShagNizSvyzSter
  oClProsKar.intShagSvyzVerhArm = FormSpecRost.TextBoxShagVerhSvyzSter
  oClProsKar.intDiamSvyzNizArm = FormSpecRost.TextBoxDiamNizSvyzSter
  oClProsKar.intDiamSvyzVerhArm = FormSpecRost.TextBoxDiamVerhSvyzSter
  oClProsKar.intCenterNizArm = FormSpecRost.TextBoxNizZachBet
  oClProsKar.intCenterVerhArm = FormSpecRost.TextBoxVerhZachBet
  'параметры для усиления
  oClProsKar.bolUsilenie = FormSpecRost.CheckBoxUsilenie.Value
  If oClProsKar.bolUsilenie = True Then
    oClProsKar.intUsLen = FormSpecRost.TextBoxUsLenSech
    oClProsKar.intUsKolKar = FormSpecRost.TextBoxUsKolSech
    oClProsKar.intUsDiamNizArm = FormSpecRost.TextBoxUsDiamNizArm
    oClProsKar.intUsDiamVerhArm = FormSpecRost.TextBoxUsDiamVerhArm
    oClProsKar.intUsShagVerhArm = FormSpecRost.TextBoxUsShagVerhArm
    oClProsKar.intUsShagNizArm = FormSpecRost.TextBoxUsShagNizArm
    oClProsKar.sUsKlassNizArm = FormSpecRost.TextBoxUsKlassNizArm
    oClProsKar.sUsKlassVerhArm = FormSpecRost.TextBoxUsKlassVerhArm
    oClProsKar.sUsGOSTNizArm = FormSpecRost.TextBoxUsGOSTNizArm
    oClProsKar.sUsGOSTVerhArm = FormSpecRost.TextBoxUsGOSTVerhArm
  End If
  oClProsKar.sKlassVerhArm = FormSpecRost.TextBoxKlassVerhArm
  oClProsKar.sKlassNizArm = FormSpecRost.TextBoxKlassNizArm
  oClProsKar.sKlassPopArm = FormSpecRost.TextBoxKlassPopArm
  oClProsKar.sKlassSvyzNizArm = FormSpecRost.TextBoxKlassSvyzNizArm
  oClProsKar.sKlassSvyzVerhArm = FormSpecRost.TextBoxKlassSvyzVerhArm
  oClProsKar.sGOSTNizArm = FormSpecRost.TextBoxGOSTNizArm
  oClProsKar.sGOSTVerhArm = FormSpecRost.TextBoxGOSTVerhArm
  oClProsKar.sGOSTPopArm = FormSpecRost.TextBoxGOSTPopArm
  oClProsKar.sGOSTSvyzNizArm = FormSpecRost.TextBoxGOSTSvyzNizArm
  oClProsKar.sGOSTSvyzVerhArm = FormSpecRost.TextBoxGOSTSvyzVerhArm

  oClProsKar.bolObrabotan = True
  
End Function

Public Function GetObjShifr(strShifr As String) As clShifr
   'возвращает объект словаря по данным из Shifr.txt по заданному шифру
   'или nothing если шифр не найден
   
   Dim strShifrMacroPath As String
   Dim strSQL As String
   Dim strConect As String
   Dim objConect As New ADODB.Connection
   Dim objRecShifr As New ADODB.Recordset
   Dim intValue As Integer
   Const strProvider As String = "Provider=Microsoft.Jet.OLEDB.4.0;"

'   strShifrMacroPath = Functions.GetMacroFolder
'   intValue = InStrRev(strShifrMacroPath, "\")
'   strShifrMacroPath = VBA.Left(strShifrMacroPath, intValue)
   strShifrMacroPath = psMacroFolder & "\Базы\Шифры.mdb"
      
   'процедура заполнения коллекции шифров из текстового файла
'   Set colShifr = Functions.GetColShifFromTXT(strMacroPath & "\Shifr.txt")
   'запрос шифра из базы
      'строка подключения
      strConect = strProvider & _
               "Data Source=" & strShifrMacroPath
      'подключение
      objConect.CursorLocation = adUseClient
      objConect.Mode = adModeWrite  'дугие смогут тоже подключатьься
      objConect.Open strConect
   'запрос шифров
   strSQL = "SELECT * FROM Шифры WHERE Шифр = '" & strShifr & "'"
   objRecShifr.Open Source:=strSQL, ActiveConnection:=objConect, _
                  CursorType:=adOpenKeyset, LockType:=adLockOptimistic, Options:=adCmdText
   If objRecShifr.EOF And objRecShifr.BOF Then
'      MsgBox "Не найден шифр в катологе!", vbExclamation
      Exit Function
   End If
   
   Set GetObjShifr = New clShifr
   If Len(objRecShifr!Адрес) <> 0 Then
      GetObjShifr.Adress = objRecShifr!Адрес
   End If
   If Len(objRecShifr!БС) <> 0 Then
      GetObjShifr.BS = objRecShifr!БС
   End If
   If Len(objRecShifr!Заказчик) <> 0 Then
      GetObjShifr.Clients = objRecShifr!Заказчик
   End If
   If Len(objRecShifr!Наимен_объекта) <> 0 Then
      GetObjShifr.ObjectName = objRecShifr!Наимен_объекта
   End If
   If Len(objRecShifr!Часть) <> 0 Then
      GetObjShifr.Part = objRecShifr!Часть
   End If
   If Len(objRecShifr!Шифр) <> 0 Then
      GetObjShifr.Shifr = objRecShifr!Шифр
   End If
   If Len(objRecShifr!Должность1) <> 0 Then
      GetObjShifr.Post1 = objRecShifr!Должность1
   End If
   If Len(objRecShifr!Должность2) <> 0 Then
      GetObjShifr.Post2 = objRecShifr!Должность2
   End If
   If Len(objRecShifr!Должность3) <> 0 Then
      GetObjShifr.Post3 = objRecShifr!Должность3
   End If
   If Len(objRecShifr!Должность4) <> 0 Then
      GetObjShifr.Post4 = objRecShifr!Должность4
   End If
   If Len(objRecShifr!Фамилия1) <> 0 Then
      GetObjShifr.Fam1 = objRecShifr!Фамилия1
   End If
   If Len(objRecShifr!Фамилия2) <> 0 Then
      GetObjShifr.Fam2 = objRecShifr!Фамилия2
   End If
   If Len(objRecShifr!Фамилия3) <> 0 Then
      GetObjShifr.Fam3 = objRecShifr!Фамилия3
   End If
   If Len(objRecShifr!Фамилия4) <> 0 Then
      GetObjShifr.Fam4 = objRecShifr!Фамилия4
   End If
   
'   'находим заданный шифр
'   On Error Resume Next
'   Set GetObjShifr = colShifr.item(strShifr)
      
End Function

Public Function GetUserFamily() As String
   'определение фамилии юзера(по имени компьютера SPD-26) из ини файла User.ini
   
   Dim oUserIni As New ClassINI
   Dim sMacroFolder As String
   Dim sUserName As String 'имя пользователя
   
   On Error GoTo HasError
   
   'определение имени пользоваттеля
   sUserName = WinAPI.ComputerName
   
   'определяем ини файл
'   sMacroFolder = GetMacroFolder(psVBProjectName)
   
   oUserIni.CreateIni "User.ini", psMacroFolder & "\Ini"
   
   GetUserFamily = oUserIni.GetFile("User", sUserName)

Exit Function
HasError:
   MsgBox Err.Description, vbExclamation, pcsVBProjectName
   
End Function

Public Function SetUserFamily(sFamely As String)
   'запись фамилии юзера(по имени компьютера SPD-26)
   
   Dim oUserIni As New ClassINI
   'Dim sMacroFolder As String
   Dim sUserName As String 'имя пользователя
   
   On Error GoTo HasError
   
   'определение имени пользоваттеля
   sUserName = WinAPI.ComputerName
   
   'определяем ини файл
'   sMacroFolder = GetMacroFolder(psVBProjectName)
   
   oUserIni.CreateIni "User.ini", psMacroFolder & "\Ini"
   
   oUserIni.WriteFile "User", sUserName, sFamely

Exit Function
HasError:
   MsgBox Err.Description, vbExclamation, pcsVBProjectName
   
End Function

Public Function RaschetMassKar() As Boolean
  'по введенным параметрам каркасов расчитываем массу арматуры
  
  Dim oKar As clKarkas
  Dim asError() As String
  Dim i As Integer
  
  ReDim asError(0)
  
  'расчет массы всех простр каркасов
  For Each oKar In pcolClProsKar
    oKar.ObrabParam
    If oKar.strError <> "" Then
      ReDim Preserve asError(i)
      asError(i) = oKar.strFirstName & ": " & oKar.strError
      i = i + 1
    End If
  Next
  'расчет массы всех плоских каркасов
  For Each oKar In pcolClPlosKar
    oKar.ObrabParam
    If oKar.strError <> "" Then
      ReDim Preserve asError(i)
      asError(i) = oKar.strFirstName & ": " & oKar.strError
      i = i + 1
    End If
  Next
  
  'если найдены ошибки
  If asError(0) <> "" Then
    FormSpecRost.TextBoxError = ""
    For i = 0 To UBound(asError)
      FormSpecRost.TextBoxError = i & " " & asError(i) & vbCr
    Next
    RaschetMassKar = False
    Exit Function
  End If
  
  RaschetMassKar = True
  
End Function

Public Sub ZapListViewProsKar(Optional intKolP As Integer, Optional sType As String)
  'заполнение листвиевера простр каркасов
  
  Dim oClProsKar As clKarkas
  Dim oListItem As ListItem
  Dim bolMarkaK As Boolean
  
  bolMarkaK = FormSpecRost.CheckBoxMarkaK.Value
  
  FormSpecRost.ListViewProsKar.ListItems.Clear
  'если вывод всех простр.каркасов
  If intKolP = 0 Then
    If sType = "Все" Or sType = "" Then
      For Each oClProsKar In pcolClProsKar
        'если при обработке имени каркаса возникли ошибки то ставим крест
        If oClProsKar.strError = "" Then
          If oClProsKar.bolObrabotan = True Then
            Set oListItem = FormSpecRost.ListViewProsKar.ListItems.Add(, , oClProsKar.strFirstName, , 1)
            oListItem.SubItems(2) = oClProsKar.sNSech
          Else
            Set oListItem = FormSpecRost.ListViewProsKar.ListItems.Add(, , oClProsKar.strFirstName)
          End If
        Else
          Set oListItem = FormSpecRost.ListViewProsKar.ListItems.Add(, , oClProsKar.strFirstName, , 2)
        End If
        oListItem.SubItems(1) = oClProsKar.intKolKar
        If bolMarkaK = True Then
          oListItem.SubItems(3) = oClProsKar.strMarkaK
        End If
      Next
    ElseIf sType = "Необработанные" Then
      For Each oClProsKar In pcolClProsKar
        If oClProsKar.bolObrabotan = False Then
          'если при обработке имени каркаса возникли ошибки то ставим крест
          If oClProsKar.strError = "" Then
            If oClProsKar.bolObrabotan = True Then
              Set oListItem = FormSpecRost.ListViewProsKar.ListItems.Add(, , oClProsKar.strFirstName, , 1)
              oListItem.SubItems(2) = oClProsKar.sNSech
            Else
              Set oListItem = FormSpecRost.ListViewProsKar.ListItems.Add(, , oClProsKar.strFirstName)
            End If
          Else
            Set oListItem = FormSpecRost.ListViewProsKar.ListItems.Add(, , oClProsKar.strFirstName, , 2)
          End If
          oListItem.SubItems(1) = oClProsKar.intKolKar
          If bolMarkaK = True Then
            oListItem.SubItems(3) = oClProsKar.strMarkaK
          End If
        End If
      Next
    End If
  Else
    For Each oClProsKar In pcolClProsKar
      If oClProsKar.intP = intKolP Then
        'если при обработке имени каркаса возникли ошибки то ставим крест
        If oClProsKar.strError = "" Then
          If oClProsKar.bolObrabotan = True Then
            Set oListItem = FormSpecRost.ListViewProsKar.ListItems.Add(, , oClProsKar.strFirstName, , 1)
            oListItem.SubItems(2) = oClProsKar.sNSech
          Else
            Set oListItem = FormSpecRost.ListViewProsKar.ListItems.Add(, , oClProsKar.strFirstName)
          End If
        Else
          Set oListItem = FormSpecRost.ListViewProsKar.ListItems.Add(, , oClProsKar.strFirstName, , 2)
        End If
        oListItem.SubItems(1) = oClProsKar.intKolKar
        If bolMarkaK = True Then
        oListItem.SubItems(3) = oClProsKar.strMarkaK
      End If
      End If
    Next
  End If
  
  'выделяем первый каркас
  If FormSpecRost.ListViewProsKar.ListItems.Count <> 0 Then
    Set oListItem = FormSpecRost.ListViewProsKar.ListItems.Item(1)
    oListItem.Selected = True
  End If
  
End Sub

Public Function RaschetSetok() As Boolean
  'расчет массы сеток
  
  Dim oSetka As clSetky
  Dim oSetkaTemp As clSetky
  Dim asError() As String
  Dim i As Integer
  
  Set pcolSetkyMarka = Nothing
  
  'определяем коллекцию сеток по маркам
  On Error Resume Next
  
  For Each oSetka In pcolClSetky
    Set oSetkaTemp = pcolSetkyMarka.Item(oSetka.psMarka)
    If Err Then
      Err.Clear
      oSetka.piKolSetok = oSetka.piKolShtuk * oSetka.piKolvoBl
      pcolSetkyMarka.Add oSetka, oSetka.psMarka
    Else
      oSetkaTemp.piKolSetok = oSetkaTemp.piKolSetok + (oSetka.piKolShtuk * oSetka.piKolvoBl)
    End If
  Next
  On Error GoTo 0
  
  ReDim asError(0)
  
  For Each oSetka In pcolSetkyMarka
    oSetka.Raschet
    If oSetka.psError <> "" Then
      ReDim Preserve asError(i)
      asError(i) = oSetka.psMarka & ": " & oSetka.psError
      i = i + 1
    End If
  Next
  
  'если найдены ошибки
  If asError(0) <> "" Then
    FormSpecRost.TextBoxError = ""
    For i = 0 To UBound(asError)
      FormSpecRost.TextBoxError = i & " " & asError(i) & vbCr
    Next
    RaschetSetok = False
    Exit Function
  End If
  
  RaschetSetok = True
  
End Function

Public Function RaschetDopSter() As Boolean
  'расчет доп стержней
  'нужно получить единую коллекцию доп стержней и расчитать массу каждого стержня
  Dim oDopSter As clDopStergen
  Dim oDopSterTemp As clDopStergen
  Dim oPlosKarSech As clPlosKarSech
  Dim oSetka As clSetky
  Dim colDopSterSech As Collection
  Dim oKar As clKarkas
  Dim iValue As Integer
  
  Set pcolAllDopStergny = Nothing
  
  '1.Объединение коллекции стержней
  'из блоков доп.стержней
  On Error Resume Next
  For Each oDopSter In pcolClDopStergny
    Set oDopSterTemp = pcolAllDopStergny.Item(oDopSter.sNaimenovanie)
    If Err Then
      'нет такого, добавляем
      Err.Clear
      pcolAllDopStergny.Add oDopSter, oDopSter.sNaimenovanie
    Else
      'добавляем кол-во
      oDopSterTemp.iKolvo = oDopSterTemp.iKolvo + oDopSter.iKolvo
    End If
  Next
  
  'смотрим усиливаемые простр.каркасы
  For Each oKar In pcolClProsKar
    If oKar.bolUsilenie = True Then
    
      'верхние усиливыающие стержни
      Set oDopSter = New clDopStergen
      oDopSter.iDiametr = oKar.intUsDiamVerhArm
      If FormSpecRost.CheckBoxMarkaK.Value = False Then
        oDopSter.iLenght = oKar.intUsLen - pclOptions.piLenSvyzB
      Else
        oDopSter.iLenght = oKar.intUsLen - pclOptions.piLenSvyzBK
      End If
      'кол-во стержней
      oDopSter.iKolvo = (oKar.intLenRab \ oKar.intUsShagVerhArm) + 1 'деление нацело
      iValue = oKar.intLenRab Mod oKar.intUsShagVerhArm
      If iValue > 25 Then oDopSter.iKolvo = oDopSter.iKolvo + 1
      oDopSter.iKolvo = oDopSter.iKolvo * oKar.intUsKolKar 'умножаем на кол каркасов (т.е. кол-во сечений)
      oDopSter.sKlassArm = oKar.sUsKlassVerhArm
      oDopSter.sGOSTArm = oKar.sUsGOSTVerhArm
      oDopSter.ObrabNaimenov
      'добавляем стержень в коллекцию
      Set oDopSterTemp = pcolAllDopStergny.Item(oDopSter.sNaimenovanie)
      If Err Then
        'нет такого, добавляем
        Err.Clear
        pcolAllDopStergny.Add oDopSter, oDopSter.sNaimenovanie
      Else
        'добавляем кол-во
        oDopSterTemp.iKolvo = oDopSterTemp.iKolvo + oDopSter.iKolvo
      End If
      
      'нижние усиливыающие стержни
      Set oDopSter = New clDopStergen
      oDopSter.iDiametr = oKar.intUsDiamNizArm
      If FormSpecRost.CheckBoxMarkaK.Value = False Then
        oDopSter.iLenght = oKar.intUsLen - pclOptions.piLenSvyzB
      Else
        oDopSter.iLenght = oKar.intUsLen - pclOptions.piLenSvyzBK
      End If
      'кол-во стержней
      oDopSter.iKolvo = oKar.intLenRab \ oKar.intUsShagNizArm + 1    'деление нацело
      iValue = oKar.intLenRab Mod oKar.intUsShagNizArm
      If iValue > 25 Then oDopSter.iKolvo = oDopSter.iKolvo + 1
      oDopSter.iKolvo = oDopSter.iKolvo * oKar.intUsKolKar 'умножаем на кол каркасов (т.е. кол-во сечений)
      oDopSter.sKlassArm = oKar.sUsKlassNizArm
      oDopSter.sGOSTArm = oKar.sUsGOSTNizArm
      oDopSter.ObrabNaimenov
      'добавляем стержень в коллекцию
      Set oDopSterTemp = pcolAllDopStergny.Item(oDopSter.sNaimenovanie)
      If Err Then
        'нет такого, добавляем
        Err.Clear
        pcolAllDopStergny.Add oDopSter, oDopSter.sNaimenovanie
      Else
        'добавляем кол-во
        oDopSterTemp.iKolvo = oDopSterTemp.iKolvo + oDopSter.iKolvo
      End If
    End If
  Next
  
  'смотрим сечения плоских каркасов
  For Each oPlosKarSech In pcolClPlosKarSech
    Set colDopSterSech = oPlosKarSech.GetColDopSter
    For Each oDopSter In colDopSterSech
      'добавляем стержни в коллекцию
      Set oDopSterTemp = pcolAllDopStergny.Item(oDopSter.sNaimenovanie)
      If Err Then
        Err.Clear
        'нет такого, добавляем
        pcolAllDopStergny.Add oDopSter, oDopSter.sNaimenovanie
      Else
        'добавляем кол-во
        oDopSterTemp.iKolvo = oDopSterTemp.iKolvo + oDopSter.iKolvo
      End If
    Next
  Next
  
  'сиотриим в сетках
  For Each oSetka In pcolClSetky
  'For Each oSetka In pcolSetkyMarka '!!! изм от 18.03.2014 - кол-во доп стержей не умножалось на кол сеток
    If oSetka.pbDopSter = True Then
      Set oDopSter = New clDopStergen
      oDopSter.iDiametr = oSetka.piDiamDopSter
      oDopSter.iLenght = oSetka.piLenDopSter
      oDopSter.iKolvo = oSetka.piKolDopSter * oSetka.piKolvoBl '!!! изм от 18.03.2014 - кол-во доп стержей не умножалось на кол блоков сеток
      oDopSter.sKlassArm = oSetka.psKlassDopSter
      oDopSter.sGOSTArm = oSetka.psGOSTDopSter
      oDopSter.ObrabNaimenov
      'добавляем стержень в коллекцию
      Set oDopSterTemp = pcolAllDopStergny.Item(oDopSter.sNaimenovanie)
      If Err Then
        'нет такого, добавляем
        Err.Clear
        pcolAllDopStergny.Add oDopSter, oDopSter.sNaimenovanie
      Else
        'добавляем кол-во
        oDopSterTemp.iKolvo = oDopSterTemp.iKolvo + oDopSter.iKolvo
      End If
    End If
  Next
  
  'смотрим в перепадах
  'обрабатывается в расчете перепадов
  
  On Error GoTo 0
  
  'расчет массы стержней
  For Each oDopSter In pcolAllDopStergny
    oDopSter.Obrab
  Next
  
  RaschetDopSter = True
  
End Function

Public Function MakeDocumentation()
  'создание чертежей спецификаций
  'Dim sFolderTablZagPath As String 'путь к папке с заготовками чертежей спецификаций
  Dim sValue As String
  
  'очищаем пути к файлам расчетов
  FormSpecRost.TextBoxFolderSpec = ""
  FormSpecRost.TextBoxFileProsPath = ""
  FormSpecRost.TextBoxFilePlosPath = ""
  FormSpecRost.TextBoxFileSodergPath = ""
  FormSpecRost.TextBoxFileTitPath = ""
  
  'создаем папку для спецификаций
  psFolderSpecPath = ThisDrawing.Path & "\Спец"
  If FormSpecRost.TextBoxShifr <> "" Then
    psFolderSpecPath = psFolderSpecPath & "_" & ReplaceInvalidCharsForFileName(FormSpecRost.TextBoxShifr)
  End If
'  If FormSpecRost.TextBoxNpart <> "" Then
    psFolderSpecPath = psFolderSpecPath & ".И-Р" & ReplaceInvalidCharsForFileName(FormSpecRost.TextBoxNpart)
'  End If
  'папка для спец-ций, результатов
  psFolderSpecPath = psFolderSpecPath & "_" & GetTimeForFolder()
  'проверяем папку
  If Dir(psFolderSpecPath, vbDirectory) <> "" Then
    RmDir psFolderSpecPath
  End If
  MkDir psFolderSpecPath
  'записываем папку спец-ий в форму
  FormSpecRost.TextBoxFolderSpec = psFolderSpecPath
  FormSpecRost.cmbExplorer.Enabled = True
  
  'файл для сохранения расчета
  psFileSaveRaschetPath = psFolderSpecPath & "\Данные-" & ReplaceInvalidCharsForFileName(FormSpecRost.TextBoxShifr) & "-Р" & ReplaceInvalidCharsForFileName(FormSpecRost.TextBoxNpart) & ".txt"
  'сохранение введенных пользователем данных
  Functions.SaveRaschet
  
  '!!!изм. 23.10.2014. Герб убрали с обложки.
'  'копирование картинки Герба
'  On Error Resume Next
'  Dim sGerb As String
'  sGerb = psMacroFolder & "\Таблицы\Герб.jpg"
'  FileCopy sGerb, psFolderSpecPath & "\Герб.jpg"
'  On Error GoTo 0

'  'временно !!!!! для тестирования
'  psMacroFolder = "\\Sgpsrv2\СПД\Конструкторы\Макросы"

   'определение фамилий для заполнения штампов и титульного листа (по галочкам из вкладки Исходных данных
   'для титула - максимум три фамилии
   'для штампов - максимум 5 фамилий
   DefinePostAndFamForSthampAndTitul
  
  'копируем чертеж плоских каркасов
  If pcolAllPlosKar.Count <> 0 Or pcolClSetky.Count <> 0 Then
    sValue = psMacroFolder & "\Таблицы\Плоские.dwg"
    psFilePlosPath = psFolderSpecPath & "\Плоские каркасы-" & ReplaceInvalidCharsForFileName(FormSpecRost.TextBoxShifr) & "-Р" & ReplaceInvalidCharsForFileName(FormSpecRost.TextBoxNpart) & ".dwg"
    FileCopy sValue, psFilePlosPath
    
    'Заполнение листов плоских каркасов
    'КД, КО, К, и сеток
    ZapDrawPlosKar psFilePlosPath
    FormSpecRost.cmbOpenPlosKar.Enabled = True
  End If
  
  'копируем чертеж простр каркасов
  If pcolClProsKar.Count <> 0 Then
    sValue = psMacroFolder & "\Таблицы\Простран.dwg"
    psFileProsPath = psFolderSpecPath & "\Простр.каркасы-" & ReplaceInvalidCharsForFileName(FormSpecRost.TextBoxShifr) & "-Р" & ReplaceInvalidCharsForFileName(FormSpecRost.TextBoxNpart) & ".dwg"
    FileCopy sValue, psFileProsPath
    
    'Заполнение чертежей простр.каркасов
    ZapDrawProsKar psFileProsPath
    FormSpecRost.cmbOpenProsKar.Enabled = True
  End If
  
  'копируем чертеж содержания
  sValue = psMacroFolder & "\Таблицы\Содержание.dwg"
  psFileSodergPath = psFolderSpecPath & "\Содержание-" & ReplaceInvalidCharsForFileName(FormSpecRost.TextBoxShifr) & "-Р" & ReplaceInvalidCharsForFileName(FormSpecRost.TextBoxNpart) & ".dwg"
  FileCopy sValue, psFileSodergPath
  'заполняем содержание
  ZapListSodefg
  FormSpecRost.cmbOpenSoderg.Enabled = True
  
  'копируем обложку
  sValue = psMacroFolder & "\Таблицы\Обложка.dwg"
  psFileTitPath = psFolderSpecPath & "\Обложка-" & ReplaceInvalidCharsForFileName(FormSpecRost.TextBoxShifr) & "-Р" & ReplaceInvalidCharsForFileName(FormSpecRost.TextBoxNpart) & ".dwg"
  FileCopy sValue, psFileTitPath
  'заполняем обложки
  ZapTitList
  FormSpecRost.cmbOpenTitul.Enabled = True
  
  'файл для спецификации элементов ростверка
  psFileSpecElemPath = psFolderSpecPath & "\Спецификация-" & ReplaceInvalidCharsForFileName(FormSpecRost.TextBoxShifr) & "-Р" & ReplaceInvalidCharsForFileName(FormSpecRost.TextBoxNpart) & ".dwg"
  'файл для ведомости расхода стали
  psFileVedomStalyPath = psFolderSpecPath & "\Ведомость-" & ReplaceInvalidCharsForFileName(FormSpecRost.TextBoxShifr) & "-Р" & ReplaceInvalidCharsForFileName(FormSpecRost.TextBoxNpart) & ".dwg"
  
  'Спец-ю эл-ов и вед-сть стали буду вставлять через insert как блок, интерактивно
  'потом разбивать
  'создание стилей для спец-ий
  'создание блока со спецификацией элементов и ведомостью расхода стали
  ZapSpecElemAndVedStaly
  FormSpecRost.cmbInsertSpec.Enabled = True
  FormSpecRost.cmbInsertVedStaly.Enabled = True
  
End Function

Public Function MakeTableStyleForSpec(Optional strTableStyleName As String = "Спецификация")
   'создание табличного стиля для спецификаций
   'для масштаба 1:1, в конкретных условиях нужно отмасштабировать после заполнения
   
   Dim strTextStyleName As String
   strTextStyleName = strTableStyleName
   Dim objTableStyle As AcadTableStyle
   Dim objTextStyle As AcadTextStyle
   Dim objDictTableStyle As AcadDictionary
   Dim bolYes As Boolean
   
   'создаем табличный стиль в словаре чертежа
   Set objDictTableStyle = ThisDrawing.Dictionaries.Item("ACAD_TABLESTYLE")
   
   'создаем текстовый стиль для таблиц
   For Each objTextStyle In ThisDrawing.TextStyles
      If objTextStyle.Name = strTextStyleName Then
         bolYes = True
      End If
   Next
   If bolYes = False Then
      Set objTextStyle = ThisDrawing.TextStyles.Add(strTextStyleName)
      'задаем шрифт, у нас принят ариал
      objTextStyle.SetFont "Arial", False, False, 0, 34 'значения получил по GetFont для нужного стиля
   End If
   
   'проверяем есть ли уже такой табл стиль
   For Each objTableStyle In objDictTableStyle
      If objTableStyle.Name = strTableStyleName Then
         'переделывать не буду ????????????
         Exit Function
      End If
   Next
'   On Error Resume Next 'не хорошо конечно, надо сделать проверки
   Set objTableStyle = objDictTableStyle.AddObject(strTableStyleName, "AcDbTableStyle")
   
'   On Error GoTo 0

   'настраиваем таблицу
   'задаем текстовый стиль всем типам ячеек
   objTableStyle.SetTextStyle AcRowType.acDataRow + AcRowType.acHeaderRow _
                           + AcRowType.acTitleRow + AcRowType.acUnknownRow, strTextStyleName
   'задаем высоту текста
   objTableStyle.SetTextHeight AcRowType.acDataRow + AcRowType.acUnknownRow, 2.5
   objTableStyle.SetTextHeight AcRowType.acHeaderRow + AcRowType.acTitleRow, 3
   'задаем выравниваниев ячейках
   objTableStyle.SetAlignment AcRowType.acHeaderRow + AcRowType.acTitleRow, acMiddleCenter
   objTableStyle.SetAlignment AcRowType.acDataRow + AcRowType.acUnknownRow, acMiddleCenter
   'задаем отступы в ячейках
   objTableStyle.HorzCellMargin = 1.5
   objTableStyle.VertCellMargin = 1
   'задаем толщины границ
   objTableStyle.SetGridLineWeight AcGridLineType.acHorzBottom + AcGridLineType.acHorzInside + AcGridLineType.acHorzTop _
                + AcGridLineType.acVertInside + AcGridLineType.acVertLeft + AcGridLineType.acVertRight, _
                AcRowType.acTitleRow + AcRowType.acHeaderRow, AcLineWeight.acLnWt050
   objTableStyle.SetGridLineWeight AcGridLineType.acHorzBottom + AcGridLineType.acHorzTop + _
               AcGridLineType.acVertInside + AcGridLineType.acVertLeft + AcGridLineType.acVertRight, _
               AcRowType.acDataRow + AcRowType.acUnknownRow, AcLineWeight.acLnWt050
   objTableStyle.SetGridLineWeight AcGridLineType.acHorzInside, _
               AcRowType.acDataRow + AcRowType.acUnknownRow, AcLineWeight.acLnWt025
'   'задаем цвет тексту
'   Dim color As AcadAcCmColor
'   'color.SetRGB 255, 0, 0
'   color.ColorIndex = acRed
'   objTableStyle.SetColor AcRowType.acDataRow + AcRowType.acHeaderRow _
'                        + AcRowType.acTitleRow + AcRowType.acUnknownRow, color
   
   'вроде все, посмотрим
   
End Function

Public Function MakeTableStyleForVed() As String
  'табличный стиль для ведомости расхода стали
  'а может и не надо, попробоваать тот же стиль что и для спец-ии эл-ов
End Function

Public Function GetFamilWithoutInitial(strFamil As String) As String
   'возвращает строку фамилии без инициалов
   'разделителем фамилии и инициалов может быть или " " или прописная буква
   
   Dim intLen As Integer
   Dim strSymbol As String
   Dim i As Integer
   
   On Error Resume Next
   
   If strFamil = "" Then
    GetFamilWithoutInitial = " "
    Exit Function
   End If
   
   intLen = InStr(strFamil, " ")
   
   'если есть пробел, то значит это пробел между фамилией и инициалами
   If intLen <> 0 Then
      GetFamilWithoutInitial = Left(strFamil, intLen - 1)
   Else
      GetFamilWithoutInitial = strFamil
   End If
   
End Function

Public Function GetTimeForFolder() As String
  'заменить ":" на ".", секунды отбросить
  Dim iValue As Integer
  
  GetTimeForFolder = Now
  
  iValue = InStrRev(GetTimeForFolder, ":")
  GetTimeForFolder = Left(GetTimeForFolder, iValue - 1)
  GetTimeForFolder = Replace(GetTimeForFolder, ":", ".")
  GetTimeForFolder = Replace(GetTimeForFolder, " ", "_")
End Function

Public Function ZapDrawPlosKar(sFilePlosKarPath As String)
  'заполнение спецификаций чертежа плоских каркасов
  
  Dim oDocPlosKar As AXDBLib.AxDbDocument
  'Dim oDocPlosKar As AcadDocument
  Dim oBlList As AcadBlockReference
  Dim oBlRamka As AcadBlockReference
  Dim oTable As AcadTable 'заполняемая таблица
  Dim oPlosKar As clKarkas
  Dim oSetka As clSetky
  Dim oListSoderg As clListSoderg
  Dim colsHeightKD As New Collection 'коллекция коллекций каркасов КД по высоте попер арм
  Dim colsHeightKO As New Collection
  Dim colsHeightK As New Collection
  Dim colsHeightType As New Collection
  Dim colPlosKarTemp As Collection
  Dim vExplode As Variant
  Dim sBlListA4 As String 'имя блока листа А4
  Dim sBlListA3 As String 'имя блока листа А3
  Dim sBlRis As String
  Dim sType As String
  Dim dListInsPt(2) As Double 'точка вставки листа
  Dim iCountKarOstalos As Integer 'оставшееся кол-во каркасов для занесения в табл
  Dim iCurRow As Integer
  Dim iTablRow As Integer 'кол-во строк в таблице
  Dim iCollectType As Integer
  Dim i As Integer
  Dim bolMarkaK As Boolean
  Dim bolListD As Boolean
  
  If pcolAllPlosKar.Count = 0 And pcolSetkyMarka.Count = 0 Then Exit Function
  
  On Error Resume Next
  
  'разделяем коллекцию плоских каркасов по высоте попер арм и типу (КД, КО,К)
  For Each oPlosKar In pcolAllPlosKar
    Select Case oPlosKar.strType
      Case "КД"
        'пихаем каркас в коллекцию по высоте попер арм
        Set colPlosKarTemp = colsHeightKD.Item(CStr(oPlosKar.intLenPopArm))
        If Err Then
          Err.Clear
          'если нет коллекции с такой высотой, создаем новую
          Set colPlosKarTemp = New Collection
          colPlosKarTemp.Add oPlosKar, oPlosKar.strPlosKarName
          'добавляем коллекцию в коллекцию :)
          colsHeightKD.Add colPlosKarTemp, CStr(oPlosKar.intLenPopArm)
        Else
          'добавляем каркас в коллекцию
          colPlosKarTemp.Add oPlosKar, oPlosKar.strPlosKarName
        End If
      Case "КО"
        'пихаем каркас в коллекцию по высоте попер арм
        Set colPlosKarTemp = colsHeightKO.Item(CStr(oPlosKar.intLenPopArm))
        If Err Then
          Err.Clear
          'если нет коллекции с такой высотой, создаем новую
          Set colPlosKarTemp = New Collection
          colPlosKarTemp.Add oPlosKar, oPlosKar.strPlosKarName
          colsHeightKO.Add colPlosKarTemp, CStr(oPlosKar.intLenPopArm)
        Else
          'добавляем каркас в коллекцию
          colPlosKarTemp.Add oPlosKar, oPlosKar.strPlosKarName
        End If
      Case "К"
        'пихаем каркас в коллекцию по высоте попер арм
        Set colPlosKarTemp = colsHeightK.Item(CStr(oPlosKar.intLenPopArm))
        If Err Then
          Err.Clear
          'если нет коллекции с такой высотой, создаем новую
          Set colPlosKarTemp = New Collection
          colPlosKarTemp.Add oPlosKar, oPlosKar.strPlosKarName
          colsHeightK.Add colPlosKarTemp, CStr(oPlosKar.intLenPopArm)
        Else
          'добавляем каркас в коллекцию
          colPlosKarTemp.Add oPlosKar, oPlosKar.strPlosKarName
        End If
      Case Else
        MsgBox "Опс. Не верный тип каркаса попался!!!"
    End Select
  Next
  
  On Error GoTo 0
  
  bolMarkaK = FormSpecRost.CheckBoxMarkaK.Value
  
  'открываем чертеж плоских каркасов
  Set oDocPlosKar = New AXDBLib.AxDbDocument
  oDocPlosKar.Open sFilePlosKarPath
'  Set oDocPlosKar = Documents.Open(sFilePlosKarPath)

'******** Заполнение спец-ий плоских каркасов КД,КО,К *****************

'повторяем для трех коллекций КД,КО,К
For iCollectType = 1 To 3

  'назначаем текущую коллекцию
  If iCollectType = 1 Then
    Set colsHeightType = colsHeightKD
    dListInsPt(1) = 320
    sBlListA4 = "ЛистА4_КД"
    sBlListA3 = "ЛистА3_КД"
'    sBlRis = "РисКД"
    sType = "КД"
  ElseIf iCollectType = 2 Then
    Set colsHeightType = colsHeightKO
    dListInsPt(1) = 320
    dListInsPt(0) = 470
    sBlListA4 = "ЛистА4_КО"
    sBlListA3 = "ЛистА3_КО"
'    sBlRis = "РисКО"
    sType = "КО"
  ElseIf iCollectType = 3 Then
    Set colsHeightType = colsHeightK
    dListInsPt(1) = 320
    dListInsPt(0) = 940
    sBlListA4 = "ЛистА4_К"
    sBlListA3 = "ЛистА3_К"
    sBlRis = "РисК"
    sType = "К"
  End If
  
  'коллекции каркасов типа , с одной высоте попер.арм.
  For Each colPlosKarTemp In colsHeightType
  
    'кол-во каркасов в коллекции этой высоты попер.арм.
    iCountKarOstalos = colPlosKarTemp.Count
    iCurRow = 1
    iTablRow = 0
    Set oListSoderg = Nothing
    For Each oPlosKar In colPlosKarTemp
    
      'есть ли место для текущего каркаса
      If iTablRow - iCurRow < 3 Then
        'дописываем наименование в рамку и в содержание заносим наименование листа
        If Not oListSoderg Is Nothing Then
          vExplode(0).TextString = GetNaimLast(vExplode(0).TextString)
          oListSoderg.psNaimenLista = vExplode(0).TextString
        End If
        'вставляем лист
        'определяем точку вставки
        dListInsPt(1) = dListInsPt(1) - 320
        'для типов каркасов КД и КО могут быть листы с "д"
        'If bolMarkaK = True Then
          If sType = "КД" Or sType = "КО" Then
            'проверяем есть ли в ближайших 13 каркасах "д" (столько каркасов на одном листе)
            If ProvBolDNear13KarInCol(colPlosKarTemp, iCountKarOstalos) = True Then
              'вставляем лист и рисунок с "д"
              If sType = "КД" Then
                Set oBlList = oDocPlosKar.ModelSpace.InsertBlock(dListInsPt, "ЛистА3_КД_д", 1, 1, 1, 0)
                sBlRis = "РисКД_д"
              ElseIf sType = "КО" Then
                Set oBlList = oDocPlosKar.ModelSpace.InsertBlock(dListInsPt, "ЛистА3_КО_д", 1, 1, 1, 0)
                sBlRis = "РисКО_д"
              End If
              bolListD = True
            Else
              bolListD = False
              If sType = "КД" Then
                sBlRis = "РисКД"
              ElseIf sType = "КО" Then
                sBlRis = "РисКО"
              End If
              If iCountKarOstalos > 4 Then
                'вставляем лист А3
                Set oBlList = oDocPlosKar.ModelSpace.InsertBlock(dListInsPt, sBlListA3, 1, 1, 1, 0)
              Else
                'вставляем лист А4
                Set oBlList = oDocPlosKar.ModelSpace.InsertBlock(dListInsPt, sBlListA4, 1, 1, 1, 0)
              End If
            End If
          Else
            bolListD = False
            If iCountKarOstalos > 4 Then
              'вставляем лист А3
              Set oBlList = oDocPlosKar.ModelSpace.InsertBlock(dListInsPt, sBlListA3, 1, 1, 1, 0)
            Else
              'вставляем лист А4
              Set oBlList = oDocPlosKar.ModelSpace.InsertBlock(dListInsPt, sBlListA4, 1, 1, 1, 0)
            End If
          End If 'sType = "КД" Or sType = "КО"
'        Else
'          If iCountKarOstalos > 4 Then
'            'вставляем лист А3
'            Set oBlList = oDocPlosKar.ModelSpace.InsertBlock(dListInsPt, sBlListA3, 1, 1, 1, 0)
'          Else
'            'вставляем лист А4
'            Set oBlList = oDocPlosKar.ModelSpace.InsertBlock(dListInsPt, sBlListA4, 1, 1, 1, 0)
'          End If
'        End If 'bolMarkaK = True
        vExplode = oBlList.Explode 'рамка и таблица
        oBlList.Delete
        For i = 0 To UBound(vExplode)
          If TypeOf vExplode(i) Is AcadBlockReference Then
            Set oBlRamka = vExplode(i)
          ElseIf TypeOf vExplode(i) Is AcadTable Then
            Set oTable = vExplode(i)
            oTable.RegenerateTableSuppressed = True
          End If
        Next 'i = 0 To UBound(vExplode)
        
        'вставляем рисунок
        Set oBlList = oDocPlosKar.ModelSpace.InsertBlock(dListInsPt, sBlRis, 1, 1, 1, 0)
          'записываем атрибуты рисунка
          vExplode = oBlList.GetAttributes
          vExplode(0).TextString = oPlosKar.intLenPopArm - 50
          vExplode(1).TextString = oPlosKar.intLenPopArm
          If sBlRis = "РисК" Or sBlRis = "РисКД_д" Or sBlRis = "РисКО_д" Then
            vExplode(2).TextString = oPlosKar.intLenPopArm - 50
            vExplode(3).TextString = oPlosKar.intLenPopArm
            If sBlRis = "РисК" Then
              If bolMarkaK = True Then
                vExplode(4).TextString = 30
                vExplode(5).TextString = 30
                vExplode(6).TextString = 30
                vExplode(7).TextString = 30
              End If
            End If
          End If
          If sBlRis = "РисКО" Then
            If FormSpecRost.CheckBoxMarkaK.Value = True Then
              vExplode(2).TextString = 30
            End If
          End If
          
'          'выравнивание положения атрибутов (т.к. в DBX слетают атрибуты с выравниванием "центр")
'          Dim oAtrRef As AcadAttributeReference
          
        iCurRow = 1 'сбрасываем номер строки
        iTablRow = oTable.Rows
        
        'записываем атрибуты рамки
        vExplode = oBlRamka.GetAttributes
        If bolMarkaK = False Then
          vExplode(0).TextString = "Каркас плоский " & oPlosKar.strPlosKarName & " ("
          vExplode(1).TextString = psShifr & "-" & oPlosKar.strPlosKarName
        Else
          vExplode(0).TextString = "Каркас плоский " & oPlosKar.strMarkaKPlos & " ("
          vExplode(1).TextString = psShifr & "-" & oPlosKar.strMarkaKPlos
        End If
        
        'Заполнение фамилий штампа
        ShtampAttrFamilyFill vExplode
        
        'создаем новый объект листа содержания и доб его в коллекцию листов
        Set oListSoderg = New clListSoderg
        pcolSoderg.Add oListSoderg
        'записываем номер листа и шифр
        oListSoderg.piStr = pcolSoderg.Count + 1  'первый лист - содержание
        vExplode(2).TextString = oListSoderg.piStr
        oListSoderg.psShifrLista = vExplode(1).TextString
      Else
        'добавляем каркас в наименование штампа
        If bolMarkaK = False Then
          vExplode(0).TextString = vExplode(0).TextString & oPlosKar.strPlosKarName & "; "
        Else
          vExplode(0).TextString = vExplode(0).TextString & oPlosKar.strMarkaKPlos & "; "
        End If
      End If 'iTablRow - (iCurRow - 1) < 3
      
      'заполняем данные каркаса в таблицу
      ZapisParamPlosKar sType, oTable, oPlosKar, iCurRow, bolMarkaK, bolListD
      
      'первая строка для след каркаса
      iCurRow = iCurRow + 3
      
      'записываем шифр листа в плос каркас
      oPlosKar.sShifrPlosKar = vExplode(1).TextString
      
      'оставшееся кол-во каркасов этой высоты
      iCountKarOstalos = iCountKarOstalos - 1
      
    Next 'oPlosKar In colPlosKarTemp
    
    'записываем окончательное наименование листа
    vExplode(0).TextString = GetNaimLast(vExplode(0).TextString)
    oListSoderg.psNaimenLista = vExplode(0).TextString
    
    'удаляем оставшиеся пустые строки в последней таблице
    i = iTablRow - iCurRow
    If i > 0 Then
      oTable.DeleteRows iCurRow, i
    End If
    
  Next 'colPlosKarTemp In colsHeightType

Next 'коллекция по типу каркасов КД,КО,К


'************* Заполнение листов сеток *************************

  If pcolClSetky.Count <> 0 Then
    
    dListInsPt(0) = 1410
    dListInsPt(1) = 320
    
    'заполняем таблицу
    For Each oSetka In pcolSetkyMarka
      
      'вставляем лист для каждой сетки
      
      'определяем точку вставки
      dListInsPt(1) = dListInsPt(1) - 320
      'вставляем лист для сетки
      Set oBlList = oDocPlosKar.ModelSpace.InsertBlock(dListInsPt, "ЛистА4_сетка", 1, 1, 1, 0)
      vExplode = oBlList.Explode 'рамка и таблица
      oBlList.Delete
      For i = 0 To UBound(vExplode)
        If TypeOf vExplode(i) Is AcadBlockReference Then
          Set oBlRamka = vExplode(i)
        ElseIf TypeOf vExplode(i) Is AcadTable Then
          Set oTable = vExplode(i)
          oTable.RegenerateTableSuppressed = True
        End If
      Next 'i = 0 To UBound(vExplode)
      'вставляем рисунок
      Set oBlList = oDocPlosKar.ModelSpace.InsertBlock(dListInsPt, "Сетка", 1, 1, 1, 0)
        'записываем атрибуты рисунка
        vExplode = oBlList.GetAttributes
        vExplode(0).TextString = oSetka.piLenghtVertik
        vExplode(1).TextString = (oSetka.piKolHorSter - 1) & "x" & oSetka.piShagHorSter
        vExplode(2).TextString = oSetka.piLenghtHoris
        vExplode(3).TextString = (oSetka.piKolVertSter - 1) & "x" & oSetka.piShagVertSter
        If oSetka.psNaimenHorSter = oSetka.psNaimenVertSter Then
          vExplode(4).TextString = 1
          vExplode(5).TextString = 1
        Else
          vExplode(4).TextString = 1
          vExplode(5).TextString = 2
        End If
        
      'записываем атрибуты рамки
        vExplode = oBlRamka.GetAttributes
        vExplode(0).TextString = "Сетка " & oSetka.psMarka
        vExplode(1).TextString = psShifr & "-" & oSetka.psMarka
        If VBA.Len(FormSpecRost.TextBoxFam6) > 11 Then 'Хисяметдинов
          vExplode(2).ScaleFactor = 0.8
        End If
        'Заполнение фамилий штампа
        ShtampAttrFamilyFill vExplode
'        vExplode(2).TextString = GetFamilWithoutInitial(FormSpecRost.TextBoxFam6)
'        vExplode(3).TextString = GetFamilWithoutInitial(FormSpecRost.TextBoxFam5)
'        vExplode(4).TextString = GetFamilWithoutInitial(FormSpecRost.TextBoxFam4)
'        vExplode(5).TextString = GetFamilWithoutInitial(FormSpecRost.TextBoxFam3)
'        vExplode(6).TextString = FormSpecRost.TextBoxPost6
'        vExplode(7).TextString = FormSpecRost.TextBoxPost5
'        vExplode(8).TextString = FormSpecRost.TextBoxPost4
'        vExplode(9).TextString = FormSpecRost.TextBoxPost3
        
        'создаем новый объект листа содержания и доб его в коллекцию листов
        Set oListSoderg = New clListSoderg
        pcolSoderg.Add oListSoderg
        'записываем номер листа и шифр
        oListSoderg.piStr = pcolSoderg.Count + 1  'первый лист - содержание
        vExplode(2).TextString = oListSoderg.piStr
        oListSoderg.psShifrLista = vExplode(1).TextString
        oListSoderg.psNaimenLista = vExplode(0).TextString
      
      'сбрасываем значение
      iCurRow = 1
      
      'заполняем параметры сетки в таблицу
      oTable.SetCellValue iCurRow, 0, oSetka.psMarka
      oTable.SetCellValue iCurRow, 1, 1
      oTable.SetCellValue iCurRow, 2, oSetka.psNaimenVertSter
      oTable.SetCellValue iCurRow, 4, FormatNumber(oSetka.pdMassaEdVertikSter, 3)  'масса одного гориз стержня
      If oSetka.psNaimenHorSter = oSetka.psNaimenVertSter Then  'если стержни одинаковые
        oTable.SetCellValue iCurRow, 3, oSetka.piKolHorSter + oSetka.piKolVertSter 'кол-во гориз стержней
      Else
        oTable.SetCellValue iCurRow, 3, oSetka.piKolVertSter 'кол-во гориз стержней
         oTable.InsertRows iCurRow + 1, 8, 1 'вставляем строчку для второй позиции
         oTable.MergeCells 1, 2, 0, 0 'объединяем ячейки марки сетки
         oTable.MergeCells 1, 2, 5, 5 'объединяем ячейки массы сетки
         oTable.SetCellValue iCurRow + 1, 1, 2
         oTable.SetCellValue iCurRow + 1, 2, oSetka.psNaimenHorSter
         oTable.SetCellValue iCurRow + 1, 3, oSetka.piKolHorSter 'кол-во вертик стержней
         oTable.SetCellValue iCurRow + 1, 4, FormatNumber(oSetka.pdMassaEdHorisSter, 3) 'масса одного вертик стержня
      End If
      oTable.SetCellValue iCurRow, 5, FormatNumber(oSetka.pdMassaSetky, 2)   'масса сетки
      'записываем ссылку на шифр чертежа сетки
      oSetka.psShifrSetki = vExplode(1).TextString
      
    Next 'oSetka In pcolClSetky
  End If 'pcolClSetky.Count <> 0
  
  'сохраняем чертеж плоских каркасов
  oDocPlosKar.SaveAs sFilePlosKarPath
 ' oDocPlosKar.Close True
  
  'записываем путь к файлу плоских каркасов в форму
  FormSpecRost.TextBoxFilePlosPath = sFilePlosKarPath
  
End Function

Public Function ZapisParamPlosKar(sTypeKar As String, oTable As AcadTable, oPlosKar As clKarkas, iCurRow As Integer, bolMarkaK As Boolean, bolListD As Boolean)
  'запись параметров плоского каркаса в таблицу
  
  Dim iColMarka As Integer
  Dim iColPoz As Integer
  Dim iColNaim As Integer
  Dim iColKol As Integer
  Dim iColMassaEd As Integer
  Dim iColMassa As Integer
  Dim iColL As Integer
  Dim iColN As Integer
  Dim iColA As Integer
  
  Select Case sTypeKar
    Case "КД"
      If bolMarkaK = True And bolListD = True Then
        iColN = 1
        iColA = 2
        iColL = 5
        iColMarka = 7
        iColPoz = 8
        iColNaim = 9
        iColKol = 10
        iColMassaEd = 11
        iColMassa = 12
        'хвосты a и b
        oTable.SetCellValue iCurRow, 2, oPlosKar.intHvostLeft
        oTable.SetCellValue iCurRow, 3, oPlosKar.intHvostRight
        oTable.SetCellValue iCurRow, 4, oPlosKar.intShagDopPopSter
        If oPlosKar.bolD = True Then
          oTable.SetCellValue iCurRow, 0, 2
        Else
          oTable.SetCellValue iCurRow, 0, 1
        End If
      Else
        iColN = 0
        iColA = 1
        iColL = 3
        iColMarka = 5
        iColPoz = 6
        iColNaim = 7
        iColKol = 8
        iColMassaEd = 9
        iColMassa = 10
        'хвосты a и b
        oTable.SetCellValue iCurRow, iColA, oPlosKar.intHvostLeft
        oTable.SetCellValue iCurRow, 2, oPlosKar.intHvostRight
      End If
    Case "КО"
      If bolMarkaK = True And bolListD = True Then
        iColA = 2
        iColN = 1
        iColL = 4
        iColMarka = 6
        iColPoz = 7
        iColNaim = 8
        iColKol = 9
        iColMassaEd = 10
        iColMassa = 11
        'хвост a
        oTable.SetCellValue iCurRow, iColA, oPlosKar.intHvostRight
        oTable.SetCellValue iCurRow, 3, oPlosKar.intShagDopPopSter
        If oPlosKar.bolD = True Then
          oTable.SetCellValue iCurRow, 0, 2
        Else
          oTable.SetCellValue iCurRow, 0, 1
        End If
      Else
        iColA = 1
        iColN = 0
        iColL = 2
        iColMarka = 4
        iColPoz = 5
        iColNaim = 6
        iColKol = 7
        iColMassaEd = 8
        iColMassa = 9
        'хвост a
        oTable.SetCellValue iCurRow, 1, oPlosKar.intHvostRight
      End If
    Case "К"
      iColN = 1
      iColL = 3
      iColMarka = 5
      iColPoz = 6
      iColNaim = 7
      iColKol = 8
      iColMassaEd = 9
      iColMassa = 10
      'рис 1,2, если есть доп.поп.стер.
      If oPlosKar.bolD = True Then
        oTable.SetCellValue iCurRow, 0, 2
        oTable.SetCellValue iCurRow, 2, oPlosKar.intShagDopPopSter
      Else
        oTable.SetCellValue iCurRow, 0, 1
        oTable.SetCellValue iCurRow, 2, 0
      End If
  End Select
  
  'первая строка описания каркаса
  oTable.SetCellValue iCurRow, iColN, oPlosKar.intN
  oTable.SetCellValue iCurRow, iColL, oPlosKar.intLenProdolArm
  If bolMarkaK = False Then
    oTable.SetCellValue iCurRow, iColMarka, oPlosKar.strPlosKarName
  Else
    oTable.SetCellValue iCurRow, iColMarka, oPlosKar.strMarkaKPlos
  End If
  oTable.SetCellValue iCurRow, iColPoz, 1  'поз.1 для верхней арматуры
  oTable.SetCellValue iCurRow + 1, iColPoz, 2 'поз. для нижней арматуры
  oTable.SetCellValue iCurRow + 2, iColPoz, 3 'поз. для поп арматуры
  oTable.SetCellValue iCurRow, iColNaim, " " & oPlosKar.sNaimVerhArm 'наимен. верхней арм
  oTable.SetCellAlignment iCurRow, iColNaim, acMiddleLeft 'выравниваем влево
  oTable.SetCellValue iCurRow + 1, iColNaim, " " & oPlosKar.sNaimNizArm 'наимен. нижней арм
  oTable.SetCellAlignment iCurRow + 1, iColNaim, acMiddleLeft 'выравниваем влево
  oTable.SetCellValue iCurRow + 2, iColNaim, " " & oPlosKar.sNaimPopArm 'наимен. поп. арм
  oTable.SetCellAlignment iCurRow + 2, iColNaim, acMiddleLeft 'выравниваем влево
  oTable.SetCellValue iCurRow, iColKol, 1 'верхняя арм. одна
  oTable.SetCellValue iCurRow + 1, iColKol, 1 'нижняя арм. одна
  oTable.SetCellValue iCurRow + 2, iColKol, oPlosKar.intKolPopSterPlosKar 'кол.поп.стержней
  oTable.SetCellValue iCurRow, iColMassaEd, FormatNumber(oPlosKar.dMassaEdVerhSter, 2) 'масса верхней арматуры
  oTable.SetCellValue iCurRow + 1, iColMassaEd, FormatNumber(oPlosKar.dMassaEdNizSter, 2) 'масса нижней арматуры
  oTable.SetCellValue iCurRow + 2, iColMassaEd, FormatNumber(oPlosKar.dMassaEdPopSter, 2)  'масса ед.поп. арматуры
  'масса каркаса
  oTable.SetCellValue iCurRow, iColMassa, FormatNumber(oPlosKar.dMassaPlosKar, 2)
  
End Function

Public Function GetNaimLast(sNaimen) As String
  'заменить последние "; " на ")"
  
  'если ";" только в конце строки, то ")" ставить не нужно
  If InStr(sNaimen, ";") = 0 Then
    GetNaimLast = Left(sNaimen, Len(sNaimen) - 2)
  Else
    GetNaimLast = Left(sNaimen, Len(sNaimen) - 2) & ")"
  End If
End Function

Public Function ZapDrawProsKar(sFileProsKarPath As String)
  'заполнение чертежей простр.каркаов
  Dim oDocProsKar As AXDBLib.AxDbDocument
  'Dim oDocProsKar As AcadDocument
  Dim oProsKar As clKarkas
  Dim oPlosKarTemp As clKarkas
  Dim oListSoderg As clListSoderg
  Dim oBlList As AcadBlockReference
  Dim oBlRamka As AcadBlockReference
  Dim oTable As AcadTable
  Dim dListInsPt(2) As Double
  Dim vExplode As Variant
  Dim iCurRow As Integer
  Dim iPolTablRows As Integer 'кол строк на первой половине таблице
  Dim iRowForKar As Integer 'кол-во строк для каркаса
  Dim iTablRows As Integer
  Dim i As Integer
  Dim bolMarkaK As Boolean
  
  If pcolClProsKar.Count = 0 Then Exit Function
  
  bolMarkaK = FormSpecRost.CheckBoxMarkaK.Value
  
  'сортировка простран каркасов для кирпички
  If bolMarkaK = True Then
    SortyrColProsKarByK pcolClProsKar
  End If
  
  'открываем чертеж плоских каркасов
  Set oDocProsKar = New AXDBLib.AxDbDocument
  oDocProsKar.Open sFileProsKarPath
  'Set oDocProsKar = Documents.Open(sFileProsKarPath)
  
  dListInsPt(1) = 320
  iPolTablRows = 31 'строк на первой половине таблицы
  iCurRow = 40 'чтобы стартануть (вставить первый лист)
  
  For Each oProsKar In pcolClProsKar
    
    'определяем кол-во строк для каркаса
    If oProsKar.sNaimSvyzVerhArm = oProsKar.sNaimSvyzNizArm Then
      iRowForKar = 3
    Else
      iRowForKar = 4
    End If
    'хватает ли строк для каркаса, в зависимости еще какая половина таблицы заполняется
    If iCurRow <= iPolTablRows Then
      'первая половина таблицы
      If iPolTablRows - (iCurRow - 1) < iRowForKar Then
        'не хватает строк, переносим текущую строку на вторую половину таблицы
'Изменения 17/08/09
'        iCurRow = iRowForKar + 1
        iCurRow = iCurRow + (iPolTablRows - (iCurRow - 1))
      End If
      
      'добавляем каркас в наименование штампа
      'If Not oTable Is Nothing Then
        If bolMarkaK = False Then
          vExplode(0).TextString = vExplode(0).TextString & oProsKar.strFirstName & "; "
        Else
          vExplode(0).TextString = vExplode(0).TextString & oProsKar.strMarkaK & "; "
        End If
      'End If
    Else
      'вторая половина таблицы
      
'Изменения 17/08/09
      If (iTablRows - 1) - (iCurRow - 1) < iRowForKar Then
'      If iTablRows - (iCurRow - 1) < iRowForKar Then

        'не хватает строк для каркаса на этом листе
        'по-хорошему нужно проверить если это последний лист, то может лучше добавить строк.
        
        'дописываем наименование листа
        If Not oListSoderg Is Nothing Then
          vExplode(0).TextString = GetNaimLast(vExplode(0).TextString)
          oListSoderg.psNaimenLista = vExplode(0).TextString
          
          'удаляем оставшиеся строки таблицы
'Изменения 17/08/09
          If iTablRows - (iCurRow - 1) > 0 Then
            oTable.DeleteRows iCurRow - 1, iTablRows - (iCurRow - 1)
          End If
'          oTable.DeleteRows iCurRow - 1, iTablRows - (iCurRow - 1)
        End If
        
        '********* вставка блока листа ************
        
        'определяем точку вставки
        dListInsPt(1) = dListInsPt(1) - 320
        Set oBlList = oDocProsKar.ModelSpace.InsertBlock(dListInsPt, "Лист", 1, 1, 1, 0)
        vExplode = oBlList.Explode 'рамка и таблица
        oBlList.Delete
        For i = 0 To UBound(vExplode)
          If TypeOf vExplode(i) Is AcadBlockReference Then
            Set oBlRamka = vExplode(i)
          ElseIf TypeOf vExplode(i) Is AcadTable Then
            Set oTable = vExplode(i)
            oTable.RegenerateTableSuppressed = True
          End If
        Next 'i = 0 To UBound(vExplode)
        
        'сбрасываем номер строки
        iCurRow = 1
        iTablRows = oTable.Rows
        
        'записываем атрибуты рамки
        vExplode = oBlRamka.GetAttributes
        If bolMarkaK = False Then
          vExplode(0).TextString = "Каркас пространственный " & oProsKar.strFirstName & " ("
          vExplode(1).TextString = psShifr & "-" & oProsKar.strFirstName
        Else
          vExplode(0).TextString = "Каркас пространственный " & oProsKar.strMarkaK & " ("
          vExplode(1).TextString = psShifr & "-" & oProsKar.strMarkaK
        End If
        
        'Заполнение фамилий в штампе
        ShtampAttrFamilyFill vExplode
        
        'создаем новый объект листа содержания и доб его в коллекцию листов
        Set oListSoderg = New clListSoderg
        pcolSoderg.Add oListSoderg
        'записываем номер листа и шифр
        oListSoderg.piStr = pcolSoderg.Count + 1  'первый лист - содержание
        vExplode(2).TextString = oListSoderg.piStr
        oListSoderg.psShifrLista = vExplode(1).TextString
      Else
        'хватает строк
        'добавляем каркас в наименование штампа
        If bolMarkaK = False Then
          vExplode(0).TextString = vExplode(0).TextString & oProsKar.strFirstName & "; "
        Else
          vExplode(0).TextString = vExplode(0).TextString & oProsKar.strMarkaK & "; "
        End If
        
      End If ''вторая половина таблицы
    End If 'хватает ли строк для каркаса
    
  '****** заполнение параметров каркаса в таблицу ******
    
      'первая строка описания каркаса
      If bolMarkaK = False Then
        oTable.SetCellValue iCurRow, 2, "\L" & oProsKar.strFirstName 'с подчеркиванием
      Else
        oTable.SetCellValue iCurRow, 2, "\L" & oProsKar.strMarkaK  'с подчеркиванием
      End If
      'oTable.SetCellAlignment iCurRow, 2, acMiddleCenter 'выравниваем по центру
      oTable.SetCellValue iCurRow, 4, "сеч." & oProsKar.sNSech & "-" & oProsKar.sNSech
      
      'составляем вторую строчку
      iCurRow = iCurRow + 1
      'находим плоский каркас в общей коллекции плоских каркасов по марке плос.кар.
      Set oPlosKarTemp = pcolAllPlosKar.Item(oProsKar.strPlosKarName)
      If VBA.Len(oPlosKarTemp.sShifrPlosKar) > 30 Then
         oTable.SetCellTextStyle iCurRow, 1, "Спец2"
      End If
      oTable.SetCellValue iCurRow, 1, " " & oPlosKarTemp.sShifrPlosKar
      oTable.SetCellAlignment iCurRow, 1, acMiddleLeft 'выравниваем влево
      If bolMarkaK = False Then
        oTable.SetCellValue iCurRow, 2, " Каркас плоский " & oProsKar.strPlosKarName
      Else
        oTable.SetCellValue iCurRow, 2, " Каркас плоский " & oProsKar.strMarkaKPlos
      End If
      oTable.SetCellAlignment iCurRow, 2, acMiddleLeft 'выравниваем влево
      oTable.SetCellValue iCurRow, 3, oProsKar.intP
      oTable.SetCellValue iCurRow, 4, FormatNumber(oProsKar.dMassaPlosKar, 2) & " кг"
      
      'проверяем, есть ли доп строка, для нижней связ. арм.
      If oProsKar.sNaimSvyzVerhArm <> oProsKar.sNaimSvyzNizArm Then
         'составляем третью строчку, для верхней связевое арм
         iCurRow = iCurRow + 1
         oTable.SetCellValue iCurRow, 2, " " & oProsKar.sNaimSvyzVerhArm
         oTable.SetCellAlignment iCurRow, 2, acMiddleLeft 'выравниваем влево
         oTable.SetCellValue iCurRow, 3, oProsKar.intKolSvyzVerhSter
         oTable.SetCellValue iCurRow, 4, FormatNumber(oProsKar.dMassaEdSvyzVerhSter, 2) & " кг"
         'составляем четвертую строчку для нижней связ.арм.
         iCurRow = iCurRow + 1
         oTable.SetCellValue iCurRow, 2, " " & oProsKar.sNaimSvyzNizArm
         oTable.SetCellAlignment iCurRow, 2, acMiddleLeft 'выравниваем влево
         oTable.SetCellValue iCurRow, 3, oProsKar.intKolSvyzNizSter
         oTable.SetCellValue iCurRow, 4, FormatNumber(oProsKar.dMassaEdSvyzNizSter, 2) & " кг"
      Else 'если нет доп.строчки
         'составляем третью строчку
         iCurRow = iCurRow + 1
         oTable.SetCellValue iCurRow, 2, " " & oProsKar.sNaimSvyzVerhArm
         oTable.SetCellAlignment iCurRow, 2, acMiddleLeft 'выравниваем влево
         oTable.SetCellValue iCurRow, 3, (oProsKar.intKolSvyzVerhSter + oProsKar.intKolSvyzNizSter)
         oTable.SetCellValue iCurRow, 4, FormatNumber(oProsKar.dMassaEdSvyzVerhSter, 2) & " кг"
      End If
      
      'строка для след каркаса
      iCurRow = iCurRow + 2
      'если перевалило на вторую половину, то начинаем с ее первой строки
      If iCurRow - iPolTablRows < 3 And iCurRow >= iPolTablRows Then
        iCurRow = iPolTablRows + 1
      End If
      
      'записываем шифр простр.каркаса
      oProsKar.sShifrProsKar = vExplode(1).TextString
      
  Next 'oProsKar In pcolClProsKar
  
  'дописываем наименование листа
  If Not oListSoderg Is Nothing Then
    vExplode(0).TextString = GetNaimLast(vExplode(0).TextString)
    oListSoderg.psNaimenLista = vExplode(0).TextString
    
    'удаляем оставшиеся строки таблицы
    oTable.DeleteRows iCurRow - 1, iTablRows - (iCurRow - 1)
  End If
  
  'сохраняем чертеж плоских каркасов
  oDocProsKar.SaveAs sFileProsKarPath
  'oDocProsKar.Close True
  
  'записываем путь к файлу простр. каркасов в форму
  FormSpecRost.TextBoxFileProsPath = sFileProsKarPath
  
End Function

Public Function GetLayer(strLayerName As String) As AcadLayer
   'возвращает объект слоя, с заданным именем
   'если слоя с таким именем не было, он создается
   
   On Error GoTo HasError
   Set GetLayer = ThisDrawing.Layers.Item(strLayerName)
   GetLayer.Lock = False
   If Not GetLayer Is pdocSpecRost.ActiveLayer Then
      GetLayer.Freeze = False
   End If
   
Exit Function

HasError:
   Set GetLayer = ThisDrawing.Layers.Add(strLayerName)
   
End Function

Public Function ZapTitList()
   'т.е заполняем обложки
   
   Dim objDoc As New AcadDocument
   'Dim objDoc As New AxDbDocument
   Dim objMS As AcadModelSpace
   Dim objBlVerhList As AcadBlockReference
   Dim objBlNigList As AcadBlockReference
   Dim objEntity As AcadEntity
   Dim objAtr As AcadAttributeReference
   Dim varAtr As Variant
   
   Set objDoc = Documents.Open(psFileTitPath)
   'objDoc.Open psFileTitPath
   Set objMS = objDoc.ModelSpace
   
   'находим блок "Обложка_верх"
   For Each objEntity In objMS
      If TypeOf objEntity Is AcadBlockReference Then
         If objEntity.Name = "Обложка_верх" Then
            Set objBlVerhList = objEntity
         ElseIf objEntity.Name = "Обложка_низ" Then
            Set objBlNigList = objEntity
         End If
      End If
   Next
      
   'заполняем атрибуты верхней обложки
   If Not objBlVerhList Is Nothing Then
      For Each varAtr In objBlVerhList.GetAttributes
         Select Case LCase(varAtr.TagString)
            Case "шифр"
               varAtr.TextString = psShifr
            Case "наимен_объекта"
               varAtr.TextString = FormSpecRost.TextBoxNaimenDoma
            Case "адрес"
               varAtr.TextString = FormSpecRost.TextBoxAdres
            Case "название_альбома"
               varAtr.TextString = FormSpecRost.TextBoxAlbum
            Case "год"
               varAtr.TextString = FormSpecRost.TextBoxYear
         End Select
      Next
   End If
   
   'заполняем атрибуты нижней обложки
   If Not objBlNigList Is Nothing Then
      For Each varAtr In objBlNigList.GetAttributes
         Select Case LCase(varAtr.TagString)
            Case "шифр"
               varAtr.TextString = psShifr
            Case "наимен_объекта"
               varAtr.TextString = FormSpecRost.TextBoxNaimenDoma
            Case "адрес"
               varAtr.TextString = FormSpecRost.TextBoxAdres
            Case "название_альбома"
               varAtr.TextString = FormSpecRost.TextBoxAlbum
            Case "год"
               varAtr.TextString = FormSpecRost.TextBoxYear
'            Case "гл_инж"
'               varAtr.TextString = "Лазарев С.В."
            Case "должность1"
               varAtr.TextString = psTitulPost1
            Case "должность2"
               varAtr.TextString = psTitulPost2
            Case "должность3"
               varAtr.TextString = psTitulPost3
            Case "фамилия1"
               varAtr.TextString = psTitulFam1
            Case "фамилия2"
               varAtr.TextString = psTitulFam2
            Case "фамилия3"
               varAtr.TextString = psTitulFam3
         End Select
      Next
   End If
   
   objDoc.Close True
   'objDoc.SaveAs psFileTitPath
   
   'записываем путь к файлу в форму
   FormSpecRost.TextBoxFileTitPath = psFileTitPath
   
End Function

Public Function ZapListSodefg()
  'заполнение листа содержания
  Dim oDocSoderg As AXDBLib.AxDbDocument
  'Dim oDocSoderg As AcadDocument
  Dim oListSoderg As clListSoderg
  Dim oBlList As AcadBlockReference
  Dim oBlRamka As AcadBlockReference
  Dim oTable As AcadTable
  Dim oTable1 As AcadTable
  Dim dListInsPt(2) As Double
  Dim vExplode As Variant
  Dim strNaimenovanie As String
  Dim strValue As String
  Dim intValue As Integer
  Dim intKolSimvolov As Integer
  Dim iCurRow As Integer
  Dim iTablRows As Integer
  Dim iKolListovSoderg As Integer
  Dim i As Integer
  
  If pcolSoderg.Count = 0 Then Exit Function
  
  'открываем чертеж
  Set oDocSoderg = New AXDBLib.AxDbDocument
  oDocSoderg.Open psFileSodergPath
'  Set oDocSoderg = Documents.Open(psFileSodergPath)
  
  dListInsPt(1) = 320
  iCurRow = 1
  intKolSimvolov = 47
  
  For Each oListSoderg In pcolSoderg
    
    'условие вставки нового листа
    If iCurRow > iTablRows Then
        
        'кол-во листов содержаний
        iKolListovSoderg = iKolListovSoderg + 1
        
        If iKolListovSoderg = 2 Then
          'исправляем наименование, на (начало)
           vExplode(0).TextString = "Содержание альбома (начало)"
        End If
        
        If iKolListovSoderg > 2 Then
          'исправляем наименование, на (продолжение)
           vExplode(0).TextString = "Содержание альбома (продолжение)"
        End If
      
        'удаляем оставшиеся строки таблицы
        If iKolListovSoderg > 1 Then
          oTable.DeleteRows iCurRow - 1, iTablRows - iCurRow
        End If
        
        '********* вставка блока листа ************
        
        'определяем точку вставки
        dListInsPt(1) = dListInsPt(1) - 320
        Set oBlList = oDocSoderg.ModelSpace.InsertBlock(dListInsPt, "ЛистА3", 1, 1, 1, 0)
        vExplode = oBlList.Explode 'рамка и таблица
        oBlList.Delete
        For i = 0 To UBound(vExplode)
          If TypeOf vExplode(i) Is AcadBlockReference Then
            Set oBlRamka = vExplode(i)
          ElseIf TypeOf vExplode(i) Is AcadTable Then
            Set oTable = vExplode(i)
            oTable.RegenerateTableSuppressed = True
          End If
        Next 'i = 0 To UBound(vExplode)
        
        'сбрасываем номер строки
        iCurRow = 1
        iTablRows = oTable.Rows
        
        'записываем атрибуты рамки
        vExplode = oBlRamka.GetAttributes
        vExplode(0).TextString = "Содержание альбома"
        vExplode(1).TextString = psShifr
        
        'Заполнение фамилий в штампе
        ShtampAttrFamilyFill vExplode
        
        'номер страницы
        vExplode(2).TextString = iKolListovSoderg
        
        'заполнием заголовок "Содержание альбома"
      'только для первого листа содержания
        If iKolListovSoderg = 1 Then
          oTable.SetCellValue iCurRow, 0, " " & psShifr
          oTable.SetCellAlignment iCurRow, 0, acMiddleLeft 'выравниваем влево
          oTable.SetCellValue iCurRow, 1, " Содержание альбома"
          oTable.SetCellAlignment iCurRow, 1, acMiddleLeft 'выравниваем влево
          oTable.SetCellValue iCurRow, 2, "Стр.1"
          iCurRow = iCurRow + 1
        End If
    
    End If ''условие вставки нового листа
    
  '****** заполнение параметров листа в таблицу ******
      
      'определяем строчку наименованя текущего описания для листа
      strNaimenovanie = oListSoderg.psNaimenLista
      'нужно удалить все пробеля из строчки
      intValue = InStr(strNaimenovanie, "(")
      If intValue <> 0 Then
        strValue = Replace(strNaimenovanie, " ", "", intValue)
        strNaimenovanie = Left(strNaimenovanie, intValue - 1) & strValue
      End If
      
'      'определяем кол-во строк, которое ему нужно, в зависимости длины строчки наименования
'      iCurRowLista = 1 'одна есть по-любому
'      intNaimen = Len(strNaimenovanie) 'опр кол-во символов в строке наименования
'      If intNaimen > intKolSimvolov Then 'если больше чем может уместиться в одной ячейке, тогда нужно разделить стрку
'         iCurRowLista = intNaimen \ intKolSimvolov 'опр целое кол-во строк по 45 символов в каждой
'         intDel = intNaimen Mod intKolSimvolov 'опредляем остаток от деления наименования на зад кол символов строки
'         If intDel > 0 Then ' прибавляем строчку
'            iCurRowLista = iCurRowLista + 1
'         End If
'      End If
'
'      'проверяем концовку первой половины таблицы, умещается ли описание всего листа или нет
'      If iCurRow <= 32 Then '32 кол-во строк на первой половине таблицы(начиная с 0)
'         intOstRow = 32 - iCurRow 'определяем оставшееся кол-во строк
'          If iCurRowLista > intOstRow + 1 Then 'если не умещается опис.кар.на оставшихся строчках, то переносим его на след половину
'              iCurRow = iCurRow + intOstRow + 1
'          End If
'      End If
      
      If VBA.Len(oListSoderg.psShifrLista) > 30 Then
         oTable.SetCellTextStyle iCurRow, 0, "Спец2"
      End If
      oTable.SetCellValue iCurRow, 0, " " & oListSoderg.psShifrLista
      oTable.SetCellAlignment iCurRow, 0, acMiddleLeft 'выравниваем влево
      oTable.SetCellValue iCurRow, 2, "Стр." & oListSoderg.piStr
      'записываем строчки наименования листа
      intValue = Len(strNaimenovanie)
      If intValue > intKolSimvolov Then 'если наимен больше чем может уместиться в одной ячейке, тогда нужно разделить стрку
         strValue = Left(strNaimenovanie, intKolSimvolov) 'строчка из первых 45 символов
         intValue = InStrRev(strValue, ";", , 1) 'пределяем номер позиции ; с конца
         If intValue > 1 Then 'если это не последний символ, то опр строку до него
            strValue = Left(strNaimenovanie, intValue) 'строка до последнего ;
            strNaimenovanie = Mid(strNaimenovanie, intValue + 1) 'оставшееся наименование
         Else 'если ; - последний символ в строке из 45 символов
            strNaimenovanie = Mid(strNaimenovanie, intKolSimvolov + 1)
         End If
         oTable.SetCellValue iCurRow, 1, " " & strValue
         oTable.SetCellAlignment iCurRow, 1, acMiddleLeft 'выравниваем влево
         
         intValue = Len(strNaimenovanie)
         While intValue > intKolSimvolov 'пока оставшаяся длина наименвания больше опр длины, будем вставлять нов строчку
            iCurRow = iCurRow + 1
            strValue = Left(strNaimenovanie, intKolSimvolov) 'строка опр длины взятой из оставшейся строчки наименования
            intValue = InStrRev(strValue, ";", , 1) 'пределяем номер позиции ; с конца
            If intValue > 1 Then 'если это не последний символ, то опр строку до него
             strValue = Left(strNaimenovanie, intValue) 'строка до последнего ;
               strNaimenovanie = Mid(strNaimenovanie, intValue + 1) 'оставшееся наименование
            Else 'если ; - последний символ в строке из 45 символов
               strNaimenovanie = Mid(strNaimenovanie, intKolSimvolov + 1)
            End If
            oTable.SetCellValue iCurRow, 1, " " & strValue
            oTable.SetCellAlignment iCurRow, 1, acMiddleLeft 'выравниваем влево
            intValue = Len(strNaimenovanie)
         Wend
         If intValue > 0 Then 'если есть остаток
            iCurRow = iCurRow + 1
            oTable.SetCellValue iCurRow, 1, " " & strNaimenovanie 'запсываем остаток
            oTable.SetCellAlignment iCurRow, 1, acMiddleLeft 'выравниваем влево
         End If
      Else 'если умещается в одной строчке
         oTable.SetCellValue iCurRow, 1, " " & strNaimenovanie
         oTable.SetCellAlignment iCurRow, 1, acMiddleLeft 'выравниваем влево
      End If
      
      'начальная строка для след описания листа
      iCurRow = iCurRow + 1
      
  Next 'лист в коллекции pcolSoderg
  
  If iKolListovSoderg > 1 Then
    'исправляем наименование, на (окончание)
    vExplode(0).TextString = "Содержание альбома (окончание)"
    'исправляем нумерацию всех проставленных везде листов на кол-во дополнительных листов содержания
    IspravNomerListov iKolListovSoderg, oDocSoderg
  End If
  
  'удаляем оставшиеся строки таблицы
  oTable.DeleteRows iCurRow, iTablRows - (iCurRow - 1)
  
  'сохраняем чертеж
  oDocSoderg.SaveAs psFileSodergPath
'  oDocSoderg.Close True
  
  'записываем путь к файлу в форму
  FormSpecRost.TextBoxFileSodergPath = psFileSodergPath
  
End Function

Public Function IspravNomerListov(iKolListovSoderg As Integer, oDocSoderg As AxDbDocument)
  'исправление номеров листов, из-за дополнительных листов содержания
  
  Dim iIzm As Integer 'прибавляемое кол-во листов
  Dim oDoc As New AxDbDocument
  Dim oMS As AcadModelSpace
  Dim oEnt As AcadEntity
  Dim oBlRef As AcadBlockReference
  Dim oTable As AcadTable
  Dim vAtr As Variant
  Dim sValue As String
  Dim iVal As Integer
  Dim i As Integer
  
  'oDocSoderg - текущий открытый документ чертеж содержания
  
  'определяем на сколько изменяется нумерация
  'определяется по кол-ву листов содержания
  iIzm = iKolListovSoderg - 1
  
  'исправляем в чертежах плоских каркасов
  oDoc.Open psFilePlosPath
  Set oMS = oDoc.ModelSpace
  For Each oEnt In oMS
    If TypeOf oEnt Is AcadBlockReference Then
      Set oBlRef = oEnt
      If oBlRef.Name Like ("Рамка") Then
        vAtr = oBlRef.GetAttributes
        vAtr(10).TextString = vAtr(10).TextString + iIzm
      End If
    End If
  Next
  oDoc.SaveAs psFilePlosPath
  
  'исправляем в чертежах простр каркасов
  oDoc.Open psFileProsPath
  Set oMS = oDoc.ModelSpace
  For Each oEnt In oMS
    If TypeOf oEnt Is AcadBlockReference Then
      Set oBlRef = oEnt
      If oBlRef.Name Like ("Рамка") Then
        vAtr = oBlRef.GetAttributes
        vAtr(10).TextString = vAtr(10).TextString + iIzm
      End If
    End If
  Next
  oDoc.SaveAs psFileProsPath
  
  'исправление в листах содержаний
  Set oMS = oDocSoderg.ModelSpace
  For Each oEnt In oMS
    If TypeOf oEnt Is AcadTable Then
      Set oTable = oEnt
      For i = 1 To oTable.Rows
        sValue = LCase(oTable.GetCellValue(i, 2))
        If sValue Like ("стр.") Then
          iVal = Val(Mid(sValue, 5)) + iIzm
          oTable.SetCellValue i, 2, iVal
        End If
      Next
    End If
  Next
  
End Function

Public Function ZapSpecElemAndVedStaly()
  'заполнение спец-ии элементов и ведомости расхода стали
  
  Dim oTable As AcadTable
  Dim oBlSpec As AcadBlock
  Dim objKarkas As clKarkas
  Dim objPlosKar As clKarkas
  Dim objKarTemp As clKarkas
  Dim objSetky As clSetky
  Dim objDopStergen As clDopStergen
  Dim objShpilka As clShpilky
  Dim oArmKlass As clArmKlas
  Dim oArmKlassDiam As clArmKlassDiam
  Dim dPtIns(2) As Double
  Dim intRow As Integer
  Dim lRandom As Long
  Dim bolMarkaK As Boolean
  
'******* Блок с таблицой спецификации элементов ростверока *************
  
  'создаем новый блок
  Randomize
  lRandom = CInt(9999 * Rnd)
  psBlSpecElem = "#U" & lRandom
  Set oBlSpec = pdocSpecRost.Blocks.Add(dPtIns, psBlSpecElem)
  
  'если такой блок уже есть, то удаляем его !!!!?????
  'или генерируем новое имя
  
  'создаем табличный стиль
  MakeTableStyleForSpec
  
  pdocSpecRost.ActiveLayer.LayerOn = True
  pdocSpecRost.ActiveLayer.Lock = False
   
   Set oTable = oBlSpec.AddTable(dPtIns, 3, 5, 8, 20)
   
   '???????? Error 01.09.2011 16.57. Обозначение не найдено.
   oTable.StyleName = "Спецификация"
   
   oTable.RegenerateTableSuppressed = True
   
'   oTable.SetRowHeight 0, 10
'   oTable.SetCellValue 0, 0, "Спецификация элементов ростверка"
   oTable.SetRowHeight 1, 15
   oTable.SetRowHeight 2, 8
   oTable.SetCellValue 1, 0, "ПОЗ"
   oTable.SetColumnWidth 0, 10
   oTable.SetCellValue 1, 1, "ОБОЗНАЧЕНИЕ"
   oTable.SetColumnWidth 1, 70
   oTable.SetCellValue 1, 2, "НАИМЕНОВАНИЕ"
   oTable.SetColumnWidth 2, 73
   oTable.SetCellValue 1, 3, "КОЛ"
   oTable.SetColumnWidth 3, 10
   oTable.SetCellValue 1, 4, "ПРИМЕЧ."
   oTable.SetColumnWidth 4, 22
   
   oTable.DeleteRows 0, 1 'удаляем строку для названия таблицы
   
   intRow = 1
  
'*********** Заполнение спец-ии элементов ростверка
  
  bolMarkaK = FormSpecRost.CheckBoxMarkaK.Value
  
  'Начинаем заполнять с Простран.каркасов
  
   intRow = 1 'в первую строку заносим заголовок, для пространственных каркасов
   oTable.SetCellValue intRow, 2, "\L" & "Каркасы пространственные" '???как подчеркивание сделать
   'oTable.SetCellAlignment intRow, 2, acMiddleCenter  'выравниваем
   'oTable.SetCellTextHeight intRow, 2, 3 'устанавливаем высоту текста 3мм(на бумаге)
  For Each objKarkas In pcolClProsKar
      intRow = intRow + 1 'увеличиваем текущую заполняемую строчку
      oTable.InsertRows intRow, 8, 1  'вставляем строчку для текущего каркаса.
      'заполняем данные каркаса в таблицу
      Set objPlosKar = pcolAllPlosKar(objKarkas.strPlosKarName)
      oTable.SetCellValue intRow, 1, " " & objPlosKar.sShifrProsKar
      oTable.SetCellAlignment intRow, 1, acMiddleLeft 'выравниваем влево
      If bolMarkaK = False Then
        oTable.SetCellValue intRow, 2, " " & objKarkas.strFirstName
      Else
        oTable.SetCellValue intRow, 2, " " & objKarkas.strMarkaK
      End If
      oTable.SetCellAlignment intRow, 2, acMiddleLeft 'выравниваем влево
      oTable.SetCellValue intRow, 3, objKarkas.intKolKar
      oTable.SetCellValue intRow, 4, FormatNumber(objKarkas.dMassaProsKar, 2) & " кг"
  Next

'******* Заполняем плоские каркасы **************
   
   '07.04.10 Сортировка
   SortyrColPlosKarByK pcolClPlosKar
   
   If pcolClPlosKar.Count <> 0 Then
   
      intRow = intRow + 1 'увеличиваем текущую заполняемую строчку
      oTable.InsertRows intRow, 8, 1  'вставляем строчку для заголовка плоских каркасов
      oTable.SetCellValue intRow, 2, "\L" & "Каркасы плоские" '
      'oTable.SetCellTextHeight intRow, 2, 3 'устанавливаем высоту текста 3мм(на бумаге)
      For Each objKarkas In pcolClPlosKar
         'если есть прост кар с таким плоским каркасом, то нужно его достать из колекции всех плоских каркасов и списать наименование его чертежа плоского каркаса
         Set objKarTemp = pcolAllPlosKar.Item(objKarkas.strPlosKarName)
        
         intRow = intRow + 1 'увеличиваем текущую заполняемую строчку
         oTable.InsertRows intRow, 8, 1  'вставляем строчку для текущего каркаса.
         'заполняем данные каркаса в таблицу
         oTable.SetCellValue intRow, 1, " " & objKarTemp.sShifrPlosKar
         oTable.SetCellAlignment intRow, 1, acMiddleLeft 'выравниваем влево
         If bolMarkaK = False Then
            oTable.SetCellValue intRow, 2, " " & objKarkas.strPlosKarName
         Else
            oTable.SetCellValue intRow, 2, " " & objKarkas.strMarkaKPlos
         End If
         oTable.SetCellAlignment intRow, 2, acMiddleLeft 'выравниваем влево
         oTable.SetCellValue intRow, 3, objKarkas.intKolKar
         oTable.SetCellValue intRow, 4, FormatNumber(objKarkas.dMassaPlosKar, 2) & " кг"
      Next
    End If
   
'******* Заполняем сетки **************

   'For Each objSetky In pcolClSetky
   For Each objSetky In pcolSetkyMarka
      intRow = intRow + 1 'увеличиваем текущую заполняемую строчку
      oTable.InsertRows intRow, 8, 1  'вставляем строчку для текущего стержня.
      'заполняем данные стержня в таблицу
      oTable.SetCellValue intRow, 1, " " & objSetky.psShifrSetki
      oTable.SetCellAlignment intRow, 1, acMiddleLeft 'выравниваем влево
      oTable.SetCellValue intRow, 2, " " & objSetky.psMarka
      oTable.SetCellAlignment intRow, 2, acMiddleLeft 'выравниваем влево
      oTable.SetCellValue intRow, 3, objSetky.piKolSetok  'кол-во сеток
      oTable.SetCellValue intRow, 4, FormatNumber(objSetky.pdMassaSetky, 2) & " кг"
   Next
   
'******* Заполняем доп стержни **************

     'проверяем есть ли Доп стержни в коллекции
  If pcolAllDopStergny.Count <> 0 Then 'если нет доп.стержней
     intRow = intRow + 1 'увеличиваем текущую заполняемую строчку
     oTable.InsertRows intRow, 8, 1  'вставляем строчку для заголовка "Изделия"
     oTable.SetCellValue intRow, 2, "\L" & "Изделия"
     'oTable.SetCellTextHeight intRow, 2, 3 'устанавливаем высоту текста 3мм(на бумаге)
    For Each objDopStergen In pcolAllDopStergny
        intRow = intRow + 1 'увеличиваем текущую заполняемую строчку
        oTable.InsertRows intRow, 8, 1  'вставляем строчку для текущего стержня.
        'заполняем данные стержня в таблицу
        If objDopStergen.iPoz <> 0 Then
          oTable.SetCellValue intRow, 0, objDopStergen.iPoz
        End If
        oTable.SetCellValue intRow, 2, " " & objDopStergen.sNaimenovanie
        oTable.SetCellAlignment intRow, 2, acMiddleLeft 'выравниваем влево
        oTable.SetCellValue intRow, 3, objDopStergen.iKolvo  'кол-во блоков доп.стер.этого диам и длины
        oTable.SetCellValue intRow, 4, FormatNumber(objDopStergen.dMassaEd, 2) & " кг"
    Next
  End If

'******* Заполняем шпильки **************

   'проверяем есть ли шпильки в коллекции
    For Each objShpilka In pcolClShpilek
      intRow = intRow + 1 'увеличиваем текущую заполняемую строчку
      oTable.InsertRows intRow, 8, 1  'вставляем строчку
      'заполняем данные шпильки в таблицу
      oTable.SetCellValue intRow, 2, " " & objShpilka.psNaimen
      oTable.SetCellAlignment intRow, 2, acMiddleLeft 'выравниваем влево
      oTable.SetCellValue intRow, 3, objShpilka.piKolvo
      oTable.SetCellValue intRow, 4, FormatNumber(objShpilka.pdMassaEd, 2) & " кг"
    Next

'******** Заполняем Материалы (Бетон) **************
      
      intRow = intRow + 1 'увеличиваем текущую заполняемую строчку
      oTable.InsertRows intRow, 8, 1  'вставляем  строчку
      oTable.SetCellValue intRow, 2, "\L" & "Материалы"
      'oTable.SetCellTextHeight intRow, 2, 3 'устанавливаем высоту текста 3мм(на бумаге)
      intRow = intRow + 1 'увеличиваем текущую заполняемую строчку
      oTable.InsertRows intRow, 8, 2  'вставляем 2 строчки
      oTable.SetCellValue intRow, 3, "?"
      oTable.SetCellAlignment intRow, 3, acMiddleCenter
      oTable.SetCellValue intRow, 2, " " & "Бетон кл.В15, W6"
      oTable.SetCellAlignment intRow, 2, acMiddleLeft 'выравниваем влево
      oTable.SetCellValue intRow, 4, "м\S3"
      intRow = intRow + 1
      oTable.SetCellValue intRow, 3, "?"
      oTable.SetCellAlignment intRow, 3, acMiddleCenter
      oTable.SetCellValue intRow, 2, " " & "Бетон кл.В7.5"
      oTable.SetCellAlignment intRow, 2, acMiddleLeft 'выравниваем влево
      oTable.SetCellValue intRow, 4, "м\S3"

  oTable.RegenerateTableSuppressed = False
  
  Dim oBlRef As AcadBlockReference
  Dim selSet As AcadSelectionSet
  Dim oEnt As AcadEntity
  Dim vExplode As Variant
  Dim dPt(2) As Double
  
  Set oBlRef = pdocSpecRost.ModelSpace.InsertBlock(dPt, psBlSpecElem, 1, 1, 1, 0)
  Set selSet = Functions.GetSelSet("Спецификация")
  vExplode = oBlRef.Explode
  oBlRef.Delete
  selSet.AddItems vExplode
  pdocSpecRost.Wblock psFileSpecElemPath, selSet
  For Each oEnt In selSet
    oEnt.Delete
  Next


'******* Блок с таблицой ведомости расхода стали *************
  
  'расчет стали по маркам и диаметрам
  RaschetStaly
  
  'создаем новый блок
  Randomize
  lRandom = CInt(9999 * Rnd)
  psBlVedStaly = "#U" & lRandom
  Set oBlSpec = pdocSpecRost.Blocks.Add(dPtIns, psBlVedStaly)
  
  'если такой блок уже есть, то удаляем его !!!!?????
  'или генерируем новое имя
  
  Dim oText As AcadText
  Dim dPtInsText(2) As Double
  Dim sText As String
  dPtInsText(0) = 2.5
  dPtInsText(1) = 2.5
  sText = "Ведомость расхода стали, кг."
  Set oText = oBlSpec.AddText(sText, dPtInsText, 3)
  
  '????????????? Error 01.09.2011 16.58 Обозначение не найдено.
  oText.StyleName = "Спецификация"
  
   Set oTable = oBlSpec.AddTable(dPtIns, 3, 1, 15, 20)
   
   '????????????? Error 01.09.2011 16.58 Обозначение не найдено.
   oTable.StyleName = "Спецификация"
   
   oTable.RegenerateTableSuppressed = True
   
'   oTable.SetRowHeight 0, 10
'   oTable.SetCellValue 0, 0, "Ведомость расхода стали, кг."
   'oTable.SetCellGridLineWeight 0, 0, AcCellEdgeMask.acTopMask, 0
  oTable.DeleteRows 0, 1 'удаляем строку название таблицы
  oTable.InsertRows 1, 8, 1 'добавляем строку для диаметров
  oTable.MergeCells 0, 1, 0, 0 'объединяем
  oTable.SetRowHeight 0, 10 'высота строки для диаметров
  oTable.SetRowHeight 1, 10 'высота строки для диаметров
  oTable.SetRowHeight 2, 15 'высота строки для диаметров
  oTable.SetCellValue 0, 0, "Марка элемента"
  oTable.SetCellValue 2, 0, "Ростверк"
  oTable.SetColumnWidth 0, 40
  
  oTable.SetCellGridLineWeight 2, 0, AcCellEdgeMask.acTopMask, AcLineWeight.acLnWt050
  
  Dim iCol As Integer
  Dim dItogo As Double
  iCol = 1
  For Each oArmKlass In pcolArmKlass
    'добавляем столбцы для класса арматуры
    oTable.InsertColumns iCol, 15, oArmKlass.colArmKlassDiam.Count
    If oArmKlass.colArmKlassDiam.Count > 1 Then
      oTable.MergeCells 0, 0, iCol, iCol + oArmKlass.colArmKlassDiam.Count - 1
    End If
    oTable.SetCellValue 0, iCol, GetKlassAndMarkaStali(oArmKlass.psKlassArm)
    For Each oArmKlassDiam In oArmKlass.colArmKlassDiam
      oTable.SetCellValue 1, iCol, "%%c" & oArmKlassDiam.piDiam
      oTable.SetCellValue 2, iCol, FormatNumber(oArmKlassDiam.pdMassa, 0)
      oTable.SetCellGridLineWeight 2, iCol, AcCellEdgeMask.acTopMask, AcLineWeight.acLnWt050
      iCol = iCol + 1
      dItogo = dItogo + oArmKlassDiam.pdMassa
    Next
  Next
  
  'всего
  oTable.InsertColumns iCol, 15, 1
  oTable.MergeCells 0, 1, iCol, iCol
  oTable.SetCellValue 0, iCol, "Всего"
  oTable.SetCellValue 2, iCol, FormatNumber(dItogo, 0)
  oTable.SetCellGridLineWeight 2, iCol, AcCellEdgeMask.acTopMask, AcLineWeight.acLnWt050
  
  oTable.RegenerateTableSuppressed = False
    
  Set oBlRef = pdocSpecRost.ModelSpace.InsertBlock(dPt, psBlVedStaly, 1, 1, 1, 0)
  Set selSet = Functions.GetSelSet("Спецификация")
  vExplode = oBlRef.Explode
  oBlRef.Delete
  'Set oEnt(0) = oBlRef
  selSet.AddItems vExplode
  pdocSpecRost.Wblock psFileVedomStalyPath, selSet
  For Each oEnt In selSet
    oEnt.Delete
  Next
  
End Function

Public Function RaschetPerepadov() As Boolean
  'расчет перепадов по листвиеверу перепадов
  Dim oSterg As clDopStergen
  Dim oStergTemp As clDopStergen
  Dim oShpilka As clShpilky
  Dim oShpilkaTemp As clShpilky
  Dim oListItem As ListItem
  Dim iKolPerepadov As Integer
  
  Set pcolClShpilek = Nothing
  
For Each oListItem In FormSpecRost.ListViewPerepady.ListItems

  iKolPerepadov = oListItem.SubItems(3)
  
  '1 Стержни по всей высоте перепада
  Set oSterg = New clDopStergen
  oSterg.iDiametr = oListItem.SubItems(6)  'piDiamSter1Perepada
  oSterg.sKlassArm = oListItem.SubItems(7) 'psKlassSter1Perepada
  oSterg.sGOSTArm = oListItem.SubItems(8) 'psGostSter1Perepada
  oSterg.iLenght = Val(oListItem.Text) + oListItem.SubItems(1) - 70
  oSterg.iKolvo = (oListItem.SubItems(4) \ 300 + 1) * 2 * iKolPerepadov
  oSterg.ObrabNaimenov
  oSterg.Obrab
  
  On Error Resume Next
  Set oStergTemp = pcolAllDopStergny.Item(oSterg.sNaimenovanie)
  If Err Then
    Err.Clear
    'нет такого стержня, добавляем
    pcolAllDopStergny.Add oSterg, oSterg.sNaimenovanie
  Else
    'добавляем кол-во
    oStergTemp.iKolvo = oStergTemp.iKolvo + oSterg.iKolvo
  End If
  On Error GoTo 0
  
  '2 Стержни по всей ширине перепада
  If Val(oListItem.SubItems(5)) > 0 Then
    Set oSterg = New clDopStergen
    oSterg.iDiametr = oListItem.SubItems(9) 'piDiamSter2Perepada
    oSterg.sKlassArm = oListItem.SubItems(10) 'psKlassSter2Perepada
    oSterg.sGOSTArm = oListItem.SubItems(11) 'psGostSter2Perepada
    oSterg.iLenght = oListItem.SubItems(4) - 20
    oSterg.iKolvo = oListItem.SubItems(5) * 2 * iKolPerepadov
    oSterg.ObrabNaimenov
    oSterg.Obrab
    
    On Error Resume Next
    Set oStergTemp = pcolAllDopStergny.Item(oSterg.sNaimenovanie)
    If Err Then
      Err.Clear
      'нет такого стержня, добавляем
      pcolAllDopStergny.Add oSterg, oSterg.sNaimenovanie
    Else
      'добавляем кол-во
      oStergTemp.iKolvo = oStergTemp.iKolvo + oSterg.iKolvo
    End If
    On Error GoTo 0
  End If 'если есть ряд шпилек
  
  '3 Стержни ширине ростверка
  If Val(oListItem.SubItems(5)) > 0 Then
    Set oSterg = New clDopStergen
    oSterg.iDiametr = oListItem.SubItems(12) 'piDiamSter3Perepada
    oSterg.sKlassArm = oListItem.SubItems(13) 'psKlassSter3Perepada
    oSterg.sGOSTArm = oListItem.SubItems(14) 'psGostSter3Perepada
    oSterg.iLenght = oListItem.SubItems(2) - 20
    oSterg.iKolvo = oListItem.SubItems(5) * 2 * iKolPerepadov
    oSterg.ObrabNaimenov
    oSterg.Obrab
    
    On Error Resume Next
    Set oStergTemp = pcolAllDopStergny.Item(oSterg.sNaimenovanie)
    If Err Then
      Err.Clear
      'нет такого стержня, добавляем
      pcolAllDopStergny.Add oSterg, oSterg.sNaimenovanie
    Else
      'добавляем кол-во
      oStergTemp.iKolvo = oStergTemp.iKolvo + oSterg.iKolvo
    End If
    On Error GoTo 0
  End If 'если есть ряд шпилек
  
  '4 Шпильки
  If Val(oListItem.SubItems(5)) > 0 Then
    Set oShpilka = New clShpilky
    oShpilka.piDiametr = oListItem.SubItems(15)
    oShpilka.psKlassArm = oListItem.SubItems(16) 'psKlassSter4Perepada
    oShpilka.psGOSTArm = oListItem.SubItems(17)
    oShpilka.piLenght = Val(oListItem.SubItems(2)) + 100
    oShpilka.piKolvo = (Val(oListItem.SubItems(4) \ 300 + 1) - 2) * oListItem.SubItems(5) * oListItem.SubItems(3) 'кол.перепадов*кол.рядов шпилек в одном перепаде
    oShpilka.Obrab
    
    On Error Resume Next
    Set oShpilkaTemp = pcolClShpilek.Item(oShpilka.psNaimen)
    If Err Then
      Err.Clear
      'нет такой шпильки, добавляем
      pcolClShpilek.Add oShpilka, oShpilka.psNaimen
    Else
      'добавляем кол-во
      oShpilkaTemp.piKolvo = oShpilkaTemp.piKolvo + oShpilka.piKolvo
    End If
    On Error GoTo 0
  End If 'если есть ряд шпилек
  
Next
  
  If Err Then
    FormSpecRost.TextBoxError = FormSpecRost.TextBoxError & " Ошибка при расчете перепадов." & Err.Description
    Exit Function
  End If

  RaschetPerepadov = True
  
End Function

Public Function RaschetStaly()
  'расчет расхода стали по маркам и диаметрам
  
  Dim oArmKlass As clArmKlas
  Dim oPlosKar As clKarkas
  Dim oProsKar As clKarkas
  Dim oDopSterg As clDopStergen
  Dim oSetka As clSetky
  Dim oShpilka As clShpilky
  Dim dMassaValue As Double
  
  Set pcolArmKlass = Nothing
  
  On Error Resume Next
  
  'перебираем все простран каркасы
  For Each oProsKar In pcolClProsKar
    'верхние стержни
    dMassaValue = oProsKar.dMassaEdVerhSter * oProsKar.intKolKar * oProsKar.intP
    Set oArmKlass = pcolArmKlass(Trim(oProsKar.sKlassVerhArm))
    If Err Then
      Err.Clear
      'усли нет, добавляем
      Set oArmKlass = New clArmKlas
      oArmKlass.psKlassArm = Trim(oProsKar.sKlassVerhArm)
      oArmKlass.AddMassaToDiam oProsKar.intDiamVerhArm, dMassaValue
      pcolArmKlass.Add oArmKlass, oArmKlass.psKlassArm
    Else
      'добавляем массу
      oArmKlass.AddMassaToDiam oProsKar.intDiamVerhArm, dMassaValue
    End If
    'нижние стержни
    dMassaValue = oProsKar.dMassaEdNizSter * oProsKar.intKolKar * oProsKar.intP
    Set oArmKlass = pcolArmKlass(Trim(oProsKar.sKlassNizArm))
    If Err Then
      Err.Clear
      'усли нет, добавляем
      Set oArmKlass = New clArmKlas
      oArmKlass.psKlassArm = Trim(oProsKar.sKlassNizArm)
      oArmKlass.AddMassaToDiam oProsKar.intDiamNizArm, dMassaValue
      pcolArmKlass.Add oArmKlass, oArmKlass.psKlassArm
    Else
      'добавляем массу
      oArmKlass.AddMassaToDiam oProsKar.intDiamNizArm, dMassaValue
    End If
    'поперкчные стержни
    dMassaValue = oProsKar.dMassaEdPopSter * oProsKar.intKolPopSterPlosKar * oProsKar.intKolKar * oProsKar.intP
    Set oArmKlass = pcolArmKlass(Trim(oProsKar.sKlassPopArm))
    If Err Then
      Err.Clear
      'усли нет, добавляем
      Set oArmKlass = New clArmKlas
      oArmKlass.psKlassArm = Trim(oProsKar.sKlassPopArm)
      oArmKlass.AddMassaToDiam oProsKar.intDiamPopArm, dMassaValue
      pcolArmKlass.Add oArmKlass, oArmKlass.psKlassArm
    Else
      'добавляем массу
      oArmKlass.AddMassaToDiam oProsKar.intDiamPopArm, dMassaValue
    End If
    
    'верхние связевые стержни
    dMassaValue = oProsKar.dMassaEdSvyzVerhSter * oProsKar.intKolSvyzVerhSter * oProsKar.intKolKar
    Set oArmKlass = pcolArmKlass(Trim(oProsKar.sKlassSvyzVerhArm))
    If Err Then
      Err.Clear
      'усли нет, добавляем
      Set oArmKlass = New clArmKlas
      oArmKlass.psKlassArm = Trim(oProsKar.sKlassSvyzVerhArm)
      oArmKlass.AddMassaToDiam oProsKar.intDiamSvyzVerhArm, dMassaValue
      pcolArmKlass.Add oArmKlass, oArmKlass.psKlassArm
    Else
      'добавляем массу
      oArmKlass.AddMassaToDiam oProsKar.intDiamSvyzVerhArm, dMassaValue
    End If
    'нижние связевые стержни
    dMassaValue = oProsKar.dMassaEdSvyzNizSter * oProsKar.intKolSvyzNizSter * oProsKar.intKolKar
    Set oArmKlass = pcolArmKlass(Trim(oProsKar.sKlassSvyzNizArm))
    If Err Then
      Err.Clear
      'усли нет, добавляем
      Set oArmKlass = New clArmKlas
      oArmKlass.psKlassArm = Trim(oProsKar.sKlassSvyzNizArm)
      oArmKlass.AddMassaToDiam oProsKar.intDiamSvyzNizArm, dMassaValue
      pcolArmKlass.Add oArmKlass, oArmKlass.psKlassArm
    Else
      'добавляем массу
      oArmKlass.AddMassaToDiam oProsKar.intDiamSvyzNizArm, dMassaValue
    End If
  Next
  
  'перебираем все плоские каркас
  For Each oPlosKar In pcolClPlosKar
    'верхние стержни
    dMassaValue = oPlosKar.dMassaEdVerhSter * oPlosKar.intKolKar
    Set oArmKlass = pcolArmKlass(Trim(oPlosKar.sKlassVerhArm))
    If Err Then
      Err.Clear
      'усли нет, добавляем
      Set oArmKlass = New clArmKlas
      oArmKlass.psKlassArm = Trim(oPlosKar.sKlassVerhArm)
      oArmKlass.AddMassaToDiam oPlosKar.intDiamVerhArm, dMassaValue
      pcolArmKlass.Add oArmKlass, oArmKlass.psKlassArm
    Else
      'добавляем массу
      oArmKlass.AddMassaToDiam oPlosKar.intDiamVerhArm, dMassaValue
    End If
    'нижние стержни
    dMassaValue = oPlosKar.dMassaEdNizSter * oPlosKar.intKolKar
    Set oArmKlass = pcolArmKlass(Trim(oPlosKar.sKlassNizArm))
    If Err Then
      Err.Clear
      'усли нет, добавляем
      Set oArmKlass = New clArmKlas
      oArmKlass.psKlassArm = Trim(oPlosKar.sKlassNizArm)
      oArmKlass.AddMassaToDiam oPlosKar.intDiamNizArm, dMassaValue
      pcolArmKlass.Add oArmKlass, oArmKlass.psKlassArm
    Else
      'добавляем массу
      oArmKlass.AddMassaToDiam oPlosKar.intDiamNizArm, dMassaValue
    End If
    'поперкчные стержни
    dMassaValue = oPlosKar.dMassaEdPopSter * oPlosKar.intKolPopSterPlosKar * oPlosKar.intKolKar
    Set oArmKlass = pcolArmKlass(Trim(oPlosKar.sKlassPopArm))
    If Err Then
      Err.Clear
      'усли нет, добавляем
      Set oArmKlass = New clArmKlas
      oArmKlass.psKlassArm = Trim(oPlosKar.sKlassPopArm)
      oArmKlass.AddMassaToDiam oPlosKar.intDiamPopArm, dMassaValue
      pcolArmKlass.Add oArmKlass, oArmKlass.psKlassArm
    Else
      'добавляем массу
      oArmKlass.AddMassaToDiam oPlosKar.intDiamPopArm, dMassaValue
    End If
  Next
  
  'доп.стержни
  For Each oDopSterg In pcolAllDopStergny
    dMassaValue = oDopSterg.dMassaEd * oDopSterg.iKolvo
    Set oArmKlass = pcolArmKlass(Trim(oDopSterg.sKlassArm))
    If Err Then
      Err.Clear
      'усли нет, добавляем
      Set oArmKlass = New clArmKlas
      oArmKlass.psKlassArm = Trim(oDopSterg.sKlassArm)
      oArmKlass.AddMassaToDiam oDopSterg.iDiametr, dMassaValue
      pcolArmKlass.Add oArmKlass, oArmKlass.psKlassArm
    Else
      'добавляем массу
      oArmKlass.AddMassaToDiam oDopSterg.iDiametr, dMassaValue
    End If
  Next
  
  'сетки
  'For Each oSetka In pcolClSetky
  For Each oSetka In pcolSetkyMarka
    'вертикальные стержни
    dMassaValue = oSetka.pdMassaEdVertikSter * oSetka.piKolVertSter * oSetka.piKolSetok
    Set oArmKlass = pcolArmKlass(Trim(oSetka.psKlassVertSter))
    If Err Then
      Err.Clear
      'усли нет, добавляем
      Set oArmKlass = New clArmKlas
      oArmKlass.psKlassArm = Trim(oSetka.psKlassVertSter)
      oArmKlass.AddMassaToDiam oSetka.piDiamVertSter, dMassaValue
      pcolArmKlass.Add oArmKlass, oArmKlass.psKlassArm
    Else
      'добавляем массу
      oArmKlass.AddMassaToDiam oSetka.piDiamVertSter, dMassaValue
    End If
    'горизонтальные стержни
    dMassaValue = oSetka.pdMassaEdHorisSter * oSetka.piKolHorSter * oSetka.piKolSetok
    Set oArmKlass = pcolArmKlass(Trim(oSetka.psKlassHorSter))
    If Err Then
      Err.Clear
      'усли нет, добавляем
      Set oArmKlass = New clArmKlas
      oArmKlass.psKlassArm = Trim(oSetka.psKlassHorSter)
      oArmKlass.AddMassaToDiam oSetka.piDiamHorSter, dMassaValue
      pcolArmKlass.Add oArmKlass, oArmKlass.psKlassArm
    Else
      'добавляем массу
      oArmKlass.AddMassaToDiam oSetka.piDiamHorSter, dMassaValue
    End If
  Next
  
  'щпильки
  For Each oShpilka In pcolClShpilek
    dMassaValue = oShpilka.pdMassaEd * oShpilka.piKolvo
    Set oArmKlass = pcolArmKlass(Trim(oShpilka.psKlassArm))
    If Err Then
      Err.Clear
      'усли нет, добавляем
      Set oArmKlass = New clArmKlas
      oArmKlass.psKlassArm = Trim(oShpilka.psKlassArm)
      oArmKlass.AddMassaToDiam oShpilka.piDiametr, dMassaValue
      pcolArmKlass.Add oArmKlass, oArmKlass.psKlassArm
    Else
      'добавляем массу
      oArmKlass.AddMassaToDiam oShpilka.piDiametr, dMassaValue
    End If
  Next
  
  'сортировка классов арматуры по классам и диаметрам
  SortyrColArmKlass pcolArmKlass
  
End Function

Public Function SaveRaschet()
  'сохранение всех введенных данных в файл
  
  Dim sValue As String
  Dim sStringToTXT As String
  Dim oKar As clKarkas
  Dim oPlosKarSech As clPlosKarSech
  Dim oSetka As clSetky
  Dim oDopSter As clDopStergen
  
'**** Запимь в текстовы файл **********
      
   On Error Resume Next
   Open psFileSaveRaschetPath For Output Access Write As #1
   
   If Err Then
      'Если файл уже открыт, попробовать закрыть
      If Err.Number = 55 Then
          Err.Clear
          Close #1
          Dim sDir1 As String
          sDir1 = Dir(psFileSaveRaschetPath)
          If sDir1 <> "" Then
            Exit Function
          End If
          Open psFileSaveRaschetPath For Output Access Write As #1
      Else
        Exit Function
      End If
   End If
   On Error GoTo 0
   
  '***** вкладка настройки
  'длины хвостов
   sValue = "Хвосты;" & FormSpecRost.TextBoxHvost0 & ";" & FormSpecRost.TextBoxHvost1 & ";" & FormSpecRost.TextBoxHvost2 & ";" & FormSpecRost.TextBoxHvost3 & ";" & FormSpecRost.TextBoxHvost4 & ";" & FormSpecRost.TextBoxHvost5 & ";" & FormSpecRost.TextBoxHvost6 & ";" & FormSpecRost.TextBoxHvost7 & ";" & FormSpecRost.TextBoxHvost8 & ";" & FormSpecRost.TextBoxHvost9 & ";"
   Print #1, sValue
  'диаметры по умолчанию
  sValue = "Диаметры_поумолчанию;" & FormSpecRost.TextBoxDiamVerhArmDef & ";" & FormSpecRost.TextBoxDiamNizArmDef & ";" & FormSpecRost.TextBoxDiamPopArmDef & ";"
  Print #1, sValue
  
  '***** пространственные каркасы
  sStringToTXT = "Пространственные каркасы"
  Print #1, sStringToTXT
  For Each oKar In pcolClProsKar
    sStringToTXT = GetStringProsKarToTxt(oKar)
    Print #1, sStringToTXT
  Next
  
  '***** плоские каркасы
  sStringToTXT = "Плоские каркасы"
  Print #1, sStringToTXT
  For Each oKar In pcolClPlosKar
    sStringToTXT = GetStringPlosKarToTxt(oKar)
    Print #1, sStringToTXT
  Next
  
  '**** параметры плоских сечений
  sStringToTXT = "Сечения плоских каркасов"
  Print #1, sStringToTXT
  For Each oPlosKarSech In pcolClPlosKarSech
    sStringToTXT = oPlosKarSech.GetStringPlosKarSechToTxt
    Print #1, sStringToTXT
  Next
  
  '*** сетки
  sStringToTXT = "Сетки"
  Print #1, sStringToTXT
  For Each oSetka In pcolClSetky
    sStringToTXT = GetStringParamSetkyToTXT(oSetka)
    Print #1, sStringToTXT
  Next
  
  '*** доп стержни
  sStringToTXT = "Доп.стержни"
  Print #1, sStringToTXT
  For Each oDopSter In pcolClDopStergny
    sStringToTXT = oDopSter.sNaimenovanie & ";" & oDopSter.iPoz & ";"
    Print #1, sStringToTXT
  Next
  
  Dim oListItem As ListItem
  '*** перепады
  sStringToTXT = "Перепады"
  Print #1, sStringToTXT
  For Each oListItem In FormSpecRost.ListViewPerepady.ListItems
    sStringToTXT = oListItem.Text & ";" & oListItem.SubItems(1) & ";" & oListItem.SubItems(2) & ";" & oListItem.SubItems(3) & ";" & oListItem.SubItems(4) & ";" & oListItem.SubItems(5) _
        & ";" & oListItem.SubItems(6) & ";" & oListItem.SubItems(7) & ";" & oListItem.SubItems(8) & ";" & oListItem.SubItems(9) & ";" & oListItem.SubItems(10) & ";" & oListItem.SubItems(11) _
        & ";" & oListItem.SubItems(12) & ";" & oListItem.SubItems(13) & ";" & oListItem.SubItems(14) & ";" & oListItem.SubItems(15) & ";" & oListItem.SubItems(16) _
        & ";" & oListItem.SubItems(17) & ";"
    Print #1, sStringToTXT
  Next
'  'стержни в перепадах
'  sStringToTXT = "Стержни в перепадах"
'  Print #1, sStringToTXT
'  sStringToTXT = FormSpecRost.TextBoxDiamSter1Perepada & ";" & FormSpecRost.TextBoxDiamSter2Perepada & ";" & FormSpecRost.TextBoxDiamSter3Perepada & ";" & FormSpecRost.TextBoxDiamSter4Perepada & ";" & FormSpecRost.TextBoxKlassSter1Perepada & ";" & FormSpecRost.TextBoxKlassSter2Perepada & ";" & FormSpecRost.TextBoxKlassSter3Perepada & ";" & FormSpecRost.TextBoxKlassSter4Perepada & ";" & FormSpecRost.TextBoxGostSter1Perepada & ";" & FormSpecRost.TextBoxGostSter2Perepada & ";" & FormSpecRost.TextBoxGostSter3Perepada & ";" & FormSpecRost.TextBoxGostSter4Perepada & ";"
'  Print #1, sStringToTXT
  
  Close #1
  
'  'Добавление расчета в SpecRost2.ini, и добавление в комбобокс расчетов
'  Dim sFileRostName As String
'  sFileRostName = pdocSpecRost.Name
'  Dim dataNow As Date
'  dataNow = Now
'  FormSpecRost.ComboBoxLoadRaschet.AddItem sFileRostName & " : " & dataNow, 0
'  FormSpecRost.ComboBoxLoadRaschet.List(0, 1) = sFileRostName
'  FormSpecRost.ComboBoxLoadRaschet.List(0, 2) = psFileSaveRaschetPath
'  FormSpecRost.ComboBoxLoadRaschet.List(0, 3) = dataNow
  
End Function

Public Function LoadRaschet(sTxtFileFullPath As String)
  'загрузка сохраненного расчета
  
  Dim sTxtString As String
  Dim oProsKar As clKarkas
  Dim oPlosKar As clKarkas
  Dim oPlosKarSech As clPlosKarSech
  Dim oSetka As clSetky
  Dim oDopSterg As clDopStergen
  
  'очищаем коллекции
  Set pcolLoadedProsKar = Nothing
  Set pcolLoadedPlosKar = Nothing
  Set pcolLoadedPlosKarSech = Nothing
  Set pcolLoadedSetky = Nothing
  Set pcolLoadedDopSterg = Nothing
  
  On Error GoTo HasError
  
'**** чтение текстового файла **********
  Close #1
  Open sTxtFileFullPath For Input Access Read As #1
  If EOF(1) = True Then Exit Function
  
  '***** вкладка настройки
  'длины хвостов
  Line Input #1, sTxtString
  If sTxtString = "" Then Exit Function
  GetHvostyFromStringTXT sTxtString
  'диаметры по умолчанию
  If EOF(1) = True Then Exit Function
  Line Input #1, sTxtString
  If sTxtString = "" Then Exit Function
  GetDiamDefFromStringTxt sTxtString
  
  '*** Простран каркасы
  If EOF(1) = True Then Exit Function
  Line Input #1, sTxtString
  If sTxtString = "" Then Exit Function
  If sTxtString = "Пространственные каркасы" Then
    If EOF(1) = True Then Exit Function
    Line Input #1, sTxtString
    Do Until sTxtString = "Плоские каркасы" Or sTxtString = ""
      Set oProsKar = GetProsKarFromTXTString(sTxtString)
      oProsKar.ObrabName oProsKar.strFirstName
      pcolLoadedProsKar.Add oProsKar, oProsKar.strFirstName
      If EOF(1) = True Then Exit Function
      Line Input #1, sTxtString
    Loop
  End If
  
  '*** Плоские каркасы
  If EOF(1) = True Then Exit Function
  Line Input #1, sTxtString
  If sTxtString = "" Then Exit Function
    Do Until sTxtString = "Сечения плоских каркасов" Or sTxtString = ""
      Set oPlosKar = GetPlosKarFromTXTString(sTxtString)
      oPlosKar.ObrabName oPlosKar.strPlosKarName
      pcolLoadedPlosKar.Add oPlosKar
      If EOF(1) = True Then Exit Function
      Line Input #1, sTxtString
    Loop
  
  '*** Сечения плоских каркасов
  If EOF(1) = True Then Exit Function
  Line Input #1, sTxtString
  If sTxtString = "" Then Exit Function
    Do Until sTxtString = "Сетки" Or sTxtString = ""
      Set oPlosKarSech = New clPlosKarSech
      oPlosKarSech.GetPlosKarSechFromTXTString sTxtString
      pcolLoadedPlosKarSech.Add oPlosKarSech
      If EOF(1) = True Then Exit Function
      Line Input #1, sTxtString
    Loop
  
  '*** Сетки
  If EOF(1) = True Then Exit Function
  Line Input #1, sTxtString
  If sTxtString = "" Then Exit Function
    Do Until sTxtString = "Доп.стержни" Or sTxtString = ""
      Set oSetka = GetSetkaFromTXTString(sTxtString)
      pcolLoadedSetky.Add oSetka
      If EOF(1) = True Then Exit Function
      Line Input #1, sTxtString
    Loop
  
  '*** Доп.стержни
  If EOF(1) = True Then Exit Function
  Line Input #1, sTxtString
  If sTxtString = "" Then Exit Function
    Do Until sTxtString = "Перепады" Or sTxtString = ""
      Set oDopSterg = GetDopStergFromTXTString(sTxtString)
      pcolLoadedDopSterg.Add oDopSterg
      If EOF(1) = True Then Exit Function
      Line Input #1, sTxtString
    Loop
  
  '*** Перепады
  If EOF(1) = True Then Exit Function
  Line Input #1, sTxtString
  If sTxtString = "" Then Exit Function
    FormSpecRost.ListViewPerepady.ListItems.Clear
    Do Until sTxtString = ""
      GetPerepadyFromTXTString (sTxtString)
      If EOF(1) = True Then Exit Function
      Line Input #1, sTxtString
    Loop
  
  Close #1
  
  
  Exit Function
HasError:
   MsgBox Err.Description, vbCritical, pcsVBProjectName
   Close #1
  
End Function

Public Function GetStringProsKarToTxt(oProsKar As clKarkas) As String
  'возвращает строку для сохранения в текстовом файле
  
  GetStringProsKarToTxt = oProsKar.strFirstName & ";" & oProsKar.sNSech & ";" & oProsKar.intLenSech & ";" & oProsKar.intHeightRost _
    & ";" & oProsKar.intShagDopPopSter & ";" & oProsKar.intCenterVerhArm & ";" & oProsKar.intCenterNizArm _
    & ";" & oProsKar.sKlassVerhArm & ";" & oProsKar.sKlassNizArm & ";" & oProsKar.sGOSTVerhArm & ";" & oProsKar.sGOSTNizArm & ";" & oProsKar.sKlassPopArm & ";" & oProsKar.sGOSTPopArm & ";" & oProsKar.intDiamSvyzVerhArm & ";" & oProsKar.intDiamSvyzNizArm & ";" & oProsKar.intShagSvyzVerhArm _
    & ";" & oProsKar.intShagSvyzNizArm & ";" & oProsKar.sKlassSvyzVerhArm & ";" & oProsKar.sKlassSvyzNizArm & ";" & oProsKar.sGOSTSvyzVerhArm & ";" & oProsKar.sGOSTSvyzNizArm & ";" & CStr(oProsKar.bolUsilenie) & ";"
  
  If oProsKar.bolUsilenie = True Then
    GetStringProsKarToTxt = GetStringProsKarToTxt & oProsKar.intUsLen & ";" & oProsKar.intUsDiamVerhArm & ";" & oProsKar.intUsDiamNizArm & ";" & oProsKar.intUsShagVerhArm & ";" & oProsKar.intUsShagNizArm & ";" & oProsKar.sUsKlassVerhArm & ";" & oProsKar.sUsKlassNizArm & ";" & oProsKar.sUsGOSTVerhArm & ";" & oProsKar.sUsGOSTNizArm & ";" & oProsKar.intUsKolKar & ";"
  End If
  
End Function

Public Function GetProsKarFromTXTString(sTxtString As String) As clKarkas
  'возвращает объект каркаса по данным из строки
  Dim sValue As String
  Dim iValue As Integer
  
  Set GetProsKarFromTXTString = New clKarkas
  
  iValue = InStr(sTxtString, ";")
  If iValue <> 0 Then
    GetProsKarFromTXTString.strFirstName = Left(sTxtString, iValue - 1)
    sTxtString = Right(sTxtString, Len(sTxtString) - iValue)
  Else
    Set GetProsKarFromTXTString = Nothing
    Exit Function
  End If
  
'  iValue = InStr(sTXTString, ";")
'  If iValue <> 0 Then
'    GetProsKarFromTXTString.strPlosKarName = Left(sTXTString, iValue - 1)
'    sTXTString = Right(sTXTString, iLen - iValue)
'  Else
'    Set GetProsKarFromTXTString = Nothing
'    Exit Function
'  End If
'  iValue = InStr(sTXTString, ";")
'  If iValue <> 0 Then
'    GetProsKarFromTXTString.strType = Left(sTXTString, iValue - 1)
'    sTXTString = Right(sTXTString, iLen - iValue)
'  Else
'    Set GetProsKarFromTXTString = Nothing
'    Exit Function
'  End If
'  iValue = InStr(sTXTString, ";")
'  If iValue <> 0 Then
'    GetProsKarFromTXTString.bolP = Left(sTXTString, iValue - 1)
'    sTXTString = Right(sTXTString, iLen - iValue)
'  Else
'    Set GetProsKarFromTXTString = Nothing
'    Exit Function
'  End If
'  iValue = InStr(sTXTString, ";")
'  If iValue <> 0 Then
'    GetProsKarFromTXTString.intN = Val(Left(sTXTString, iValue - 1))
'    sTXTString = Right(sTXTString, iLen - iValue)
'  Else
'    Set GetProsKarFromTXTString = Nothing
'    Exit Function
'  End If
'  iValue = InStr(sTXTString, ";")
'  If iValue <> 0 Then
'    GetProsKarFromTXTString.intP = Val(Left(sTXTString, iValue - 1))
'    sTXTString = Right(sTXTString, iLen - iValue)
'  Else
'    Set GetProsKarFromTXTString = Nothing
'    Exit Function
'  End If
'  iValue = InStr(sTXTString, ";")
'  If iValue <> 0 Then
'    GetProsKarFromTXTString.intKolKar = Val(Left(sTXTString, iValue - 1))
'    sTXTString = Right(sTXTString, iLen - iValue)
'  Else
'    Set GetProsKarFromTXTString = Nothing
'    Exit Function
'  End If
  iValue = InStr(sTxtString, ";")
  If iValue <> 0 Then
    GetProsKarFromTXTString.sNSech = Left(sTxtString, iValue - 1)
    sTxtString = Right(sTxtString, Len(sTxtString) - iValue)
  Else
    Set GetProsKarFromTXTString = Nothing
    Exit Function
  End If
  iValue = InStr(sTxtString, ";")
  If iValue <> 0 Then
    GetProsKarFromTXTString.intLenSech = Val(Left(sTxtString, iValue - 1))
    sTxtString = Right(sTxtString, Len(sTxtString) - iValue)
  Else
    Set GetProsKarFromTXTString = Nothing
    Exit Function
  End If
  iValue = InStr(sTxtString, ";")
  If iValue <> 0 Then
    GetProsKarFromTXTString.intHeightRost = Val(Left(sTxtString, iValue - 1))
    sTxtString = Right(sTxtString, Len(sTxtString) - iValue)
  Else
    Set GetProsKarFromTXTString = Nothing
    Exit Function
  End If
'  iValue = InStr(sTXTString, ";")
'  If iValue <> 0 Then
'    GetProsKarFromTXTString.bolHeightRostInName = Left(sTXTString, iValue - 1)
'    sTXTString = Right(sTXTString, iLen - iValue)
'  Else
'    Set GetProsKarFromTXTString = Nothing
'    Exit Function
'  End If
'  iValue = InStr(sTXTString, ";")
'  If iValue <> 0 Then
'    GetProsKarFromTXTString.bolD = Left(sTXTString, iValue - 1)
'    sTXTString = Right(sTXTString, iLen - iValue)
'  Else
'    Set GetProsKarFromTXTString = Nothing
'    Exit Function
'  End If
  iValue = InStr(sTxtString, ";")
  If iValue <> 0 Then
    GetProsKarFromTXTString.intShagDopPopSter = Val(Left(sTxtString, iValue - 1))
    sTxtString = Right(sTxtString, Len(sTxtString) - iValue)
  Else
    Set GetProsKarFromTXTString = Nothing
    Exit Function
  End If
'  iValue = InStr(sTXTString, ";")
'  If iValue <> 0 Then
'    GetProsKarFromTXTString.intHvostLeft = Val(Left(sTXTString, iValue - 1))
'    sTXTString = Right(sTXTString, iLen - iValue)
'  Else
'    Set GetProsKarFromTXTString = Nothing
'    Exit Function
'  End If
'  iValue = InStr(sTXTString, ";")
'  If iValue <> 0 Then
'    GetProsKarFromTXTString.intHvostRight = Val(Left(sTXTString, iValue - 1))
'    sTXTString = Right(sTXTString, iLen - iValue)
'  Else
'    Set GetProsKarFromTXTString = Nothing
'    Exit Function
'  End If
  iValue = InStr(sTxtString, ";")
  If iValue <> 0 Then
    GetProsKarFromTXTString.intCenterVerhArm = Val(Left(sTxtString, iValue - 1))
    sTxtString = Right(sTxtString, Len(sTxtString) - iValue)
  Else
    Set GetProsKarFromTXTString = Nothing
    Exit Function
  End If
  iValue = InStr(sTxtString, ";")
  If iValue <> 0 Then
    GetProsKarFromTXTString.intCenterNizArm = Val(Left(sTxtString, iValue - 1))
    sTxtString = Right(sTxtString, Len(sTxtString) - iValue)
  Else
    Set GetProsKarFromTXTString = Nothing
    Exit Function
  End If
'  iValue = InStr(sTXTString, ";")
'  If iValue <> 0 Then
'    GetProsKarFromTXTString.intDiamVerhArm = Val(Left(sTXTString, iValue - 1))
'    sTXTString = Right(sTXTString, iLen - iValue)
'  Else
'    Set GetProsKarFromTXTString = Nothing
'    Exit Function
'  End If
'  iValue = InStr(sTXTString, ";")
'  If iValue <> 0 Then
'    GetProsKarFromTXTString.intDiamNizArm = Val(Left(sTXTString, iValue - 1))
'    sTXTString = Right(sTXTString, iLen - iValue)
'  Else
'    Set GetProsKarFromTXTString = Nothing
'    Exit Function
'  End If
  iValue = InStr(sTxtString, ";")
  If iValue <> 0 Then
    GetProsKarFromTXTString.sKlassVerhArm = Left(sTxtString, iValue - 1)
    sTxtString = Right(sTxtString, Len(sTxtString) - iValue)
  Else
    Set GetProsKarFromTXTString = Nothing
    Exit Function
  End If
  iValue = InStr(sTxtString, ";")
  If iValue <> 0 Then
    GetProsKarFromTXTString.sKlassNizArm = Left(sTxtString, iValue - 1)
    sTxtString = Right(sTxtString, Len(sTxtString) - iValue)
  Else
    Set GetProsKarFromTXTString = Nothing
    Exit Function
  End If
  iValue = InStr(sTxtString, ";")
  If iValue <> 0 Then
    GetProsKarFromTXTString.sGOSTVerhArm = Left(sTxtString, iValue - 1)
    sTxtString = Right(sTxtString, Len(sTxtString) - iValue)
  Else
    Set GetProsKarFromTXTString = Nothing
    Exit Function
  End If
  iValue = InStr(sTxtString, ";")
  If iValue <> 0 Then
    GetProsKarFromTXTString.sGOSTNizArm = Left(sTxtString, iValue - 1)
    sTxtString = Right(sTxtString, Len(sTxtString) - iValue)
  Else
    Set GetProsKarFromTXTString = Nothing
    Exit Function
  End If
'  iValue = InStr(sTXTString, ";")
'  If iValue <> 0 Then
'    GetProsKarFromTXTString.intDiamPopArm = Val(Left(sTXTString, iValue - 1))
'    sTXTString = Right(sTXTString, iLen - iValue)
'  Else
'    Set GetProsKarFromTXTString = Nothing
'    Exit Function
'  End If
  iValue = InStr(sTxtString, ";")
  If iValue <> 0 Then
    GetProsKarFromTXTString.sKlassPopArm = Left(sTxtString, iValue - 1)
    sTxtString = Right(sTxtString, Len(sTxtString) - iValue)
  Else
    Set GetProsKarFromTXTString = Nothing
    Exit Function
  End If
  iValue = InStr(sTxtString, ";")
  If iValue <> 0 Then
    GetProsKarFromTXTString.sGOSTPopArm = Left(sTxtString, iValue - 1)
    sTxtString = Right(sTxtString, Len(sTxtString) - iValue)
  Else
    Set GetProsKarFromTXTString = Nothing
    Exit Function
  End If
  iValue = InStr(sTxtString, ";")
  If iValue <> 0 Then
    GetProsKarFromTXTString.intDiamSvyzVerhArm = Val(Left(sTxtString, iValue - 1))
    sTxtString = Right(sTxtString, Len(sTxtString) - iValue)
  Else
    Set GetProsKarFromTXTString = Nothing
    Exit Function
  End If
  iValue = InStr(sTxtString, ";")
  If iValue <> 0 Then
    GetProsKarFromTXTString.intDiamSvyzNizArm = Val(Left(sTxtString, iValue - 1))
    sTxtString = Right(sTxtString, Len(sTxtString) - iValue)
  Else
    Set GetProsKarFromTXTString = Nothing
    Exit Function
  End If
  iValue = InStr(sTxtString, ";")
  If iValue <> 0 Then
    GetProsKarFromTXTString.intShagSvyzVerhArm = Val(Left(sTxtString, iValue - 1))
    sTxtString = Right(sTxtString, Len(sTxtString) - iValue)
  Else
    Set GetProsKarFromTXTString = Nothing
    Exit Function
  End If
  iValue = InStr(sTxtString, ";")
  If iValue <> 0 Then
    GetProsKarFromTXTString.intShagSvyzNizArm = Val(Left(sTxtString, iValue - 1))
    sTxtString = Right(sTxtString, Len(sTxtString) - iValue)
  Else
    Set GetProsKarFromTXTString = Nothing
    Exit Function
  End If
  iValue = InStr(sTxtString, ";")
  If iValue <> 0 Then
    GetProsKarFromTXTString.sKlassSvyzVerhArm = Left(sTxtString, iValue - 1)
    sTxtString = Right(sTxtString, Len(sTxtString) - iValue)
  Else
    Set GetProsKarFromTXTString = Nothing
    Exit Function
  End If
  iValue = InStr(sTxtString, ";")
  If iValue <> 0 Then
    GetProsKarFromTXTString.sKlassSvyzNizArm = Left(sTxtString, iValue - 1)
    sTxtString = Right(sTxtString, Len(sTxtString) - iValue)
  Else
    Set GetProsKarFromTXTString = Nothing
    Exit Function
  End If
  iValue = InStr(sTxtString, ";")
  If iValue <> 0 Then
    GetProsKarFromTXTString.sGOSTSvyzVerhArm = Left(sTxtString, iValue - 1)
    sTxtString = Right(sTxtString, Len(sTxtString) - iValue)
  Else
    Set GetProsKarFromTXTString = Nothing
    Exit Function
  End If
  iValue = InStr(sTxtString, ";")
  If iValue <> 0 Then
    GetProsKarFromTXTString.sGOSTSvyzNizArm = Left(sTxtString, iValue - 1)
    sTxtString = Right(sTxtString, Len(sTxtString) - iValue)
  Else
    Set GetProsKarFromTXTString = Nothing
    Exit Function
  End If
  iValue = InStr(sTxtString, ";")
  If iValue <> 0 Then
    GetProsKarFromTXTString.bolUsilenie = Left(sTxtString, iValue - 1)
    sTxtString = Right(sTxtString, Len(sTxtString) - iValue)
  Else
    Set GetProsKarFromTXTString = Nothing
    Exit Function
  End If
  If GetProsKarFromTXTString.bolUsilenie = True Then
    iValue = InStr(sTxtString, ";")
    If iValue <> 0 Then
      GetProsKarFromTXTString.intUsLen = Val(Left(sTxtString, iValue - 1))
      sTxtString = Right(sTxtString, Len(sTxtString) - iValue)
    Else
      Set GetProsKarFromTXTString = Nothing
      Exit Function
    End If
    iValue = InStr(sTxtString, ";")
    If iValue <> 0 Then
      GetProsKarFromTXTString.intUsDiamVerhArm = Val(Left(sTxtString, iValue - 1))
      sTxtString = Right(sTxtString, Len(sTxtString) - iValue)
    Else
      Set GetProsKarFromTXTString = Nothing
      Exit Function
    End If
    iValue = InStr(sTxtString, ";")
    If iValue <> 0 Then
      GetProsKarFromTXTString.intUsDiamNizArm = Val(Left(sTxtString, iValue - 1))
      sTxtString = Right(sTxtString, Len(sTxtString) - iValue)
    Else
      Set GetProsKarFromTXTString = Nothing
      Exit Function
    End If
    iValue = InStr(sTxtString, ";")
    If iValue <> 0 Then
      GetProsKarFromTXTString.intUsShagVerhArm = Val(Left(sTxtString, iValue - 1))
      sTxtString = Right(sTxtString, Len(sTxtString) - iValue)
    Else
      Set GetProsKarFromTXTString = Nothing
      Exit Function
    End If
    iValue = InStr(sTxtString, ";")
    If iValue <> 0 Then
      GetProsKarFromTXTString.intUsShagNizArm = Val(Left(sTxtString, iValue - 1))
      sTxtString = Right(sTxtString, Len(sTxtString) - iValue)
    Else
      Set GetProsKarFromTXTString = Nothing
      Exit Function
    End If
    iValue = InStr(sTxtString, ";")
    If iValue <> 0 Then
      GetProsKarFromTXTString.sUsKlassVerhArm = Left(sTxtString, iValue - 1)
      sTxtString = Right(sTxtString, Len(sTxtString) - iValue)
    Else
      Set GetProsKarFromTXTString = Nothing
      Exit Function
    End If
    iValue = InStr(sTxtString, ";")
    If iValue <> 0 Then
      GetProsKarFromTXTString.sUsKlassNizArm = Left(sTxtString, iValue - 1)
      sTxtString = Right(sTxtString, Len(sTxtString) - iValue)
    Else
      Set GetProsKarFromTXTString = Nothing
      Exit Function
    End If
    iValue = InStr(sTxtString, ";")
    If iValue <> 0 Then
      GetProsKarFromTXTString.sUsGOSTVerhArm = Left(sTxtString, iValue - 1)
      sTxtString = Right(sTxtString, Len(sTxtString) - iValue)
    Else
      Set GetProsKarFromTXTString = Nothing
      Exit Function
    End If
    iValue = InStr(sTxtString, ";")
    If iValue <> 0 Then
      GetProsKarFromTXTString.sUsGOSTNizArm = Left(sTxtString, iValue - 1)
      sTxtString = Right(sTxtString, Len(sTxtString) - iValue)
    Else
      Set GetProsKarFromTXTString = Nothing
      Exit Function
    End If
    iValue = InStr(sTxtString, ";")
    If iValue <> 0 Then
      GetProsKarFromTXTString.intUsKolKar = Left(sTxtString, iValue - 1)
      sTxtString = Right(sTxtString, Len(sTxtString) - iValue)
    Else
      Exit Function
    End If
  End If 'усиление
  
End Function

Public Function GetPlosKarFromTXTString(sTxtString As String) As clKarkas
  'возвращает объект каркаса по данным из строки
  Dim sValue As String
  Dim iValue As Integer
  
  Set GetPlosKarFromTXTString = New clKarkas
  
  iValue = InStr(sTxtString, ";")
  If iValue <> 0 Then
    GetPlosKarFromTXTString.strPlosKarName = Left(sTxtString, iValue - 1)
    sTxtString = Right(sTxtString, Len(sTxtString) - iValue)
  Else
    Set GetPlosKarFromTXTString = Nothing
    Exit Function
  End If
  iValue = InStr(sTxtString, ";")
  If iValue <> 0 Then
    GetPlosKarFromTXTString.intHeightRost = Val(Left(sTxtString, iValue - 1))
    sTxtString = Right(sTxtString, Len(sTxtString) - iValue)
  Else
    Set GetPlosKarFromTXTString = Nothing
    Exit Function
  End If
  iValue = InStr(sTxtString, ";")
  If iValue <> 0 Then
    GetPlosKarFromTXTString.intCenterVerhArm = Val(Left(sTxtString, iValue - 1))
    sTxtString = Right(sTxtString, Len(sTxtString) - iValue)
  Else
    Set GetPlosKarFromTXTString = Nothing
    Exit Function
  End If
  iValue = InStr(sTxtString, ";")
  If iValue <> 0 Then
    GetPlosKarFromTXTString.intCenterNizArm = Val(Left(sTxtString, iValue - 1))
    sTxtString = Right(sTxtString, Len(sTxtString) - iValue)
  Else
    Set GetPlosKarFromTXTString = Nothing
    Exit Function
  End If
  iValue = InStr(sTxtString, ";")
  If iValue <> 0 Then
    GetPlosKarFromTXTString.sKlassVerhArm = Left(sTxtString, iValue - 1)
    sTxtString = Right(sTxtString, Len(sTxtString) - iValue)
  Else
    Set GetPlosKarFromTXTString = Nothing
    Exit Function
  End If
  iValue = InStr(sTxtString, ";")
  If iValue <> 0 Then
    GetPlosKarFromTXTString.sGOSTVerhArm = Left(sTxtString, iValue - 1)
    sTxtString = Right(sTxtString, Len(sTxtString) - iValue)
  Else
    Set GetPlosKarFromTXTString = Nothing
    Exit Function
  End If
  iValue = InStr(sTxtString, ";")
  If iValue <> 0 Then
    GetPlosKarFromTXTString.sKlassNizArm = Left(sTxtString, iValue - 1)
    sTxtString = Right(sTxtString, Len(sTxtString) - iValue)
  Else
    Set GetPlosKarFromTXTString = Nothing
    Exit Function
  End If
  iValue = InStr(sTxtString, ";")
  If iValue <> 0 Then
    GetPlosKarFromTXTString.sGOSTNizArm = Left(sTxtString, iValue - 1)
    sTxtString = Right(sTxtString, Len(sTxtString) - iValue)
  Else
    Set GetPlosKarFromTXTString = Nothing
    Exit Function
  End If
  iValue = InStr(sTxtString, ";")
  If iValue <> 0 Then
    GetPlosKarFromTXTString.sKlassPopArm = Left(sTxtString, iValue - 1)
    sTxtString = Right(sTxtString, Len(sTxtString) - iValue)
  Else
    Set GetPlosKarFromTXTString = Nothing
    Exit Function
  End If
  iValue = InStr(sTxtString, ";")
  If iValue <> 0 Then
    GetPlosKarFromTXTString.sGOSTPopArm = Left(sTxtString, iValue - 1)
    sTxtString = Right(sTxtString, Len(sTxtString) - iValue)
  Else
    Set GetPlosKarFromTXTString = Nothing
    Exit Function
  End If
  iValue = InStr(sTxtString, ";")
  If iValue <> 0 Then
    GetPlosKarFromTXTString.intShagDopPopSter = Val(Left(sTxtString, iValue - 1))
    sTxtString = Right(sTxtString, Len(sTxtString) - iValue)
  Else
    Set GetPlosKarFromTXTString = Nothing
    Exit Function
  End If

End Function

Public Function GetStringPlosKarToTxt(oPlosKar As clKarkas) As String
  'возвращает строчку пармаметров плоского каркаса для записи в txt
  GetStringPlosKarToTxt = oPlosKar.strPlosKarName & ";" & oPlosKar.intHeightRost & ";" & oPlosKar.intCenterVerhArm & ";" & oPlosKar.intCenterNizArm & ";" & oPlosKar.sKlassVerhArm & ";" & oPlosKar.sGOSTVerhArm & ";" & oPlosKar.sKlassNizArm & ";" & oPlosKar.sGOSTNizArm & ";" & oPlosKar.sKlassPopArm & ";" & oPlosKar.sGOSTPopArm & ";" & oPlosKar.intShagDopPopSter & ";"
End Function

Public Function GetStringParamSetkyToTXT(oSetka As clSetky) As String
  'возвращает строку с параметрами сетки для записи в txt
  
  GetStringParamSetkyToTXT = oSetka.psBlName & ";" & oSetka.piShagVertSter & ";" & oSetka.piShagHorSter & ";" & oSetka.piKolShagovHoris & ";" & oSetka.piKolShagovVertik & ";" & oSetka.piDiamVertSter & ";" & oSetka.piDiamHorSter _
    & ";" & oSetka.psKlassVertSter & ";" & oSetka.psKlassHorSter & ";" & oSetka.psGOSTVertSter & ";" & oSetka.psGOSTHorSter _
    & ";" & oSetka.pbDopSter & ";"
  
  If oSetka.pbDopSter = True Then
    GetStringParamSetkyToTXT = GetStringParamSetkyToTXT & ";" & oSetka.piDiamDopSter & ";" & oSetka.piLenDopSter & ";" & oSetka.piKolDopSter & ";" & oSetka.psKlassDopSter & ";" & oSetka.psGOSTDopSter & ";"
  End If
End Function

Public Function SortyrColArmKlass(colArmKlass As Collection)
  'сортировка коллекции объектов классов арматуры по классу и диаметру
  Dim i As Integer
  Dim j As Integer
  Dim k As Integer
  Dim oArmKlassTemp As clArmKlas
  Dim oArmKlass As clArmKlas
  Dim oArmKlassDiamTemp As clArmKlassDiam
  
  For i = 1 To colArmKlass.Count - 1
    For j = 1 To colArmKlass.Count - i
      'проверяем
      If StrComp(colArmKlass(j).psKlassArm, colArmKlass(j + 1).psKlassArm, vbTextCompare) = -1 Then
        Set oArmKlassTemp = colArmKlass(j)
        colArmKlass.Remove j
        colArmKlass.Add oArmKlassTemp, oArmKlassTemp.psKlassArm, , j
      End If
    Next
  Next
  
  For Each oArmKlass In colArmKlass
    'сортируем диаметры
    For i = 1 To oArmKlass.colArmKlassDiam.Count - 1
      For j = 1 To oArmKlass.colArmKlassDiam.Count - i
        If oArmKlass.colArmKlassDiam(j).piDiam > oArmKlass.colArmKlassDiam(j + 1).piDiam Then
          Set oArmKlassDiamTemp = oArmKlass.colArmKlassDiam(j)
          oArmKlass.colArmKlassDiam.Remove j
          oArmKlass.colArmKlassDiam.Add oArmKlassDiamTemp, , , j
        End If
      Next
    Next
  Next
  
End Function

Public Function GetHvostyFromStringTXT(sTxtString As String)
  'запись параметров вкладки настройки из строки данных
  Dim sValue As String
  Dim iValue As Integer
  
  iValue = InStr(sTxtString, ";")
  If iValue <> 0 Then
    sValue = Left(sTxtString, iValue - 1)
    If sValue <> "Хвосты" Then Exit Function
    sTxtString = Right(sTxtString, Len(sTxtString) - iValue)
  End If
  iValue = InStr(sTxtString, ";")
  If iValue <> 0 Then
    FormSpecRost.TextBoxHvost0 = Val(Left(sTxtString, iValue - 1))
    sTxtString = Right(sTxtString, Len(sTxtString) - iValue)
  End If
  iValue = InStr(sTxtString, ";")
  If iValue <> 0 Then
    FormSpecRost.TextBoxHvost1 = Val(Left(sTxtString, iValue - 1))
    sTxtString = Right(sTxtString, Len(sTxtString) - iValue)
  End If
  iValue = InStr(sTxtString, ";")
  If iValue <> 0 Then
    FormSpecRost.TextBoxHvost2 = Val(Left(sTxtString, iValue - 1))
    sTxtString = Right(sTxtString, Len(sTxtString) - iValue)
  End If
  iValue = InStr(sTxtString, ";")
  If iValue <> 0 Then
    FormSpecRost.TextBoxHvost3 = Val(Left(sTxtString, iValue - 1))
    sTxtString = Right(sTxtString, Len(sTxtString) - iValue)
  End If
  iValue = InStr(sTxtString, ";")
  If iValue <> 0 Then
    FormSpecRost.TextBoxHvost4 = Val(Left(sTxtString, iValue - 1))
    sTxtString = Right(sTxtString, Len(sTxtString) - iValue)
  End If
  iValue = InStr(sTxtString, ";")
  If iValue <> 0 Then
    FormSpecRost.TextBoxHvost5 = Val(Left(sTxtString, iValue - 1))
    sTxtString = Right(sTxtString, Len(sTxtString) - iValue)
  End If
  iValue = InStr(sTxtString, ";")
  If iValue <> 0 Then
    FormSpecRost.TextBoxHvost6 = Val(Left(sTxtString, iValue - 1))
    sTxtString = Right(sTxtString, Len(sTxtString) - iValue)
  End If
  iValue = InStr(sTxtString, ";")
  If iValue <> 0 Then
    FormSpecRost.TextBoxHvost7 = Val(Left(sTxtString, iValue - 1))
    sTxtString = Right(sTxtString, Len(sTxtString) - iValue)
  End If
  iValue = InStr(sTxtString, ";")
  If iValue <> 0 Then
    FormSpecRost.TextBoxHvost8 = Val(Left(sTxtString, iValue - 1))
    sTxtString = Right(sTxtString, Len(sTxtString) - iValue)
  End If
  iValue = InStr(sTxtString, ";")
  If iValue <> 0 Then
    FormSpecRost.TextBoxHvost9 = Val(Left(sTxtString, iValue - 1))
    sTxtString = Right(sTxtString, Len(sTxtString) - iValue)
  End If
  
End Function

Public Function GetDiamDefFromStringTxt(sTxtString As String)
  'заполнение полей диаметров по умолчанию из строки файла txt
  Dim sValue As String
  Dim iValue As Integer
  
  iValue = InStr(sTxtString, ";")
  If iValue <> 0 Then
    sValue = Left(sTxtString, iValue - 1)
    If sValue <> "Диаметры_поумолчанию" Then Exit Function
    sTxtString = Right(sTxtString, Len(sTxtString) - iValue)
  End If
  iValue = InStr(sTxtString, ";")
  If iValue <> 0 Then
    FormSpecRost.TextBoxDiamVerhArmDef = Val(Left(sTxtString, iValue - 1))
    sTxtString = Right(sTxtString, Len(sTxtString) - iValue)
  End If
  iValue = InStr(sTxtString, ";")
  If iValue <> 0 Then
    FormSpecRost.TextBoxDiamNizArmDef = Val(Left(sTxtString, iValue - 1))
    sTxtString = Right(sTxtString, Len(sTxtString) - iValue)
  End If
  iValue = InStr(sTxtString, ";")
  If iValue <> 0 Then
    FormSpecRost.TextBoxDiamPopArmDef = Val(Left(sTxtString, iValue - 1))
    sTxtString = Right(sTxtString, Len(sTxtString) - iValue)
  End If
  
End Function

Public Function GetMarkaKFromBlock(oBlRef As AcadBlockReference) As String
  'определяем значение атрибута маркиК
  Dim vAtr As Variant
  
  For Each vAtr In oBlRef.GetAttributes
    If UCase(vAtr.TagString) = UCase(pclOptions.psMarkaKTag) Then
      GetMarkaKFromBlock = vAtr.TextString
      Exit For
    End If
  Next
  
End Function

Public Function ProvMarokKInColKar(colKar As Collection) As String
  'проверка номеров марокК  каркасов
  Dim oKar As clKarkas
  Dim oKarTest As clKarkas
  Dim colMarokK As New Collection
  Dim i As Integer
  Dim sError As String
  
  On Error Resume Next
  For Each oKar In colKar
    colMarokK.Add oKar, oKar.strMarkaKPlos
    If Err Then
      Err.Clear
      'т.е. уже есть такая маркаК
      'проверяем настоящее имя плоского каркаса
      If oKar.strPlosKarName <> colMarokK(oKar.strMarkaKPlos).strPlosKarName Then
        sError = "Одна марка у разных каркасов: " & oKar.strFirstName & "=" & oKar.strMarkaKPlos & " и у " & colMarokK(oKar.strMarkaKPlos).strFirstName & "=" & colMarokK(oKar.strMarkaKPlos).strMarkaKPlos & vbCrLf
      End If
    End If
  Next
  
  ProvMarokKInColKar = sError
  
End Function

Public Function PrimLoadedObjects()
  'применение загруженных объектов расчета к выбранным блокам
  
  If pcolClProsKar.Count <> 0 And pcolLoadedProsKar.Count <> 0 Then
    PrimLoadedProsKar
  End If
  If pcolClPlosKar.Count <> 0 And pcolLoadedPlosKar.Count <> 0 Then
    PrimLoadedPlosKar
  End If
  If pcolClDopStergny.Count <> 0 And pcolLoadedDopSterg.Count <> 0 Then
    PrimLoadedDopStergny
  End If
  If pcolClSetky.Count <> 0 And pcolLoadedSetky.Count <> 0 Then
    PrimLoadedSetky
  End If
  
End Function

Private Function PrimLoadedProsKar()
  'применение загруженных объектов простр каркасов к коллекции простр каркасов
  Dim oLoadedKar As clKarkas
  Dim oKar As clKarkas
  
  For Each oLoadedKar In pcolLoadedProsKar
On Error Resume Next
    Set oKar = pcolClProsKar(oLoadedKar.strFirstName)
    If Err Then
On Error GoTo 0
      'нет такого каркаса
    Else
      'применяем параматры загруженного каркаса
      'сохраняем неизменяемые значения
      oKar.sNSech = oLoadedKar.sNSech
      oKar.intLenSech = oLoadedKar.intLenSech
      oKar.intHeightRost = oLoadedKar.intHeightRost
      oKar.intShagDopPopSter = oLoadedKar.intShagDopPopSter
      oKar.intCenterNizArm = oLoadedKar.intCenterNizArm
      oKar.intCenterVerhArm = oLoadedKar.intCenterVerhArm
      oKar.sKlassNizArm = oLoadedKar.sKlassNizArm
      oKar.sKlassVerhArm = oLoadedKar.sKlassVerhArm
      oKar.sKlassPopArm = oLoadedKar.sKlassPopArm
      oKar.sGOSTNizArm = oLoadedKar.sGOSTNizArm
      oKar.sGOSTVerhArm = oLoadedKar.sGOSTVerhArm
      oKar.sGOSTPopArm = oLoadedKar.sGOSTPopArm
      oKar.intDiamSvyzNizArm = oLoadedKar.intDiamSvyzNizArm
      oKar.intDiamSvyzVerhArm = oLoadedKar.intDiamSvyzVerhArm
      oKar.intShagSvyzVerhArm = oLoadedKar.intShagSvyzVerhArm
      oKar.intShagSvyzNizArm = oLoadedKar.intShagSvyzNizArm
      oKar.sKlassSvyzNizArm = oLoadedKar.sKlassSvyzNizArm
      oKar.sKlassSvyzVerhArm = oLoadedKar.sKlassSvyzVerhArm
      oKar.sGOSTSvyzNizArm = oLoadedKar.sGOSTSvyzNizArm
      oKar.sGOSTSvyzVerhArm = oLoadedKar.sGOSTSvyzVerhArm
      oKar.bolUsilenie = oLoadedKar.bolUsilenie
      If oKar.bolUsilenie = True Then
        oKar.intUsLen = oLoadedKar.intUsLen
        oKar.intUsKolKar = oLoadedKar.intUsKolKar
        oKar.intUsDiamNizArm = oLoadedKar.intUsDiamNizArm
        oKar.intUsDiamVerhArm = oLoadedKar.intUsDiamVerhArm
        oKar.intUsShagNizArm = oLoadedKar.intUsShagNizArm
        oKar.intUsShagVerhArm = oLoadedKar.intUsShagVerhArm
        oKar.sUsKlassNizArm = oLoadedKar.sUsKlassNizArm
        oKar.sUsKlassVerhArm = oLoadedKar.sUsKlassVerhArm
        oKar.sUsGOSTNizArm = oLoadedKar.sUsGOSTNizArm
        oKar.sUsGOSTVerhArm = oLoadedKar.sUsGOSTVerhArm
      End If
      oKar.bolObrabotan = True
    End If
  Next
  
  'обновляем список в листвиевере
  Functions.ZapListViewProsKar
  
End Function

Private Function PrimLoadedPlosKar()
  'применение загруженных объектов плоских каркасов к коллекции простр каркасов
  Dim oLoadedKar As clKarkas
  Dim oKar As clKarkas
  Dim oPlosSech As clPlosKarSech
  Dim oLoadedPlosSech As clPlosKarSech
  Dim oListItem As ListItem
  
  For Each oLoadedKar In pcolLoadedPlosKar
On Error Resume Next
    Set oKar = pcolClPlosKar(oLoadedKar.strPlosKarName)
    If Err Then
On Error GoTo 0
      'нет такого каркаса
    Else
      'применяем параматры загруженного каркаса
      'сохраняем неизменяемые значения
      oKar.intHeightRost = oLoadedKar.intHeightRost
      oKar.intCenterVerhArm = oLoadedKar.intCenterVerhArm
      oKar.intCenterNizArm = oLoadedKar.intCenterNizArm
      oKar.sKlassVerhArm = oLoadedKar.sKlassVerhArm
      oKar.sKlassNizArm = oLoadedKar.sKlassNizArm
      oKar.sKlassPopArm = oLoadedKar.sKlassPopArm
      oKar.sGOSTVerhArm = oLoadedKar.sGOSTVerhArm
      oKar.sGOSTNizArm = oLoadedKar.sGOSTNizArm
      oKar.sGOSTPopArm = oLoadedKar.sGOSTPopArm
      oKar.bolObrabotan = True
    End If
  Next
  
  'обработка сечений плолских каркасов
  For Each oLoadedPlosSech In pcolLoadedPlosKarSech
On Error Resume Next
    Set oPlosSech = pcolClPlosKarSech(oLoadedPlosSech.sMarkaPlosKar)
    If Err Then
On Error GoTo 0
      'нет такого каркаса
    Else
      'применяем параматры загруженного каркаса
      'сохраняем неизменяемые значения
      oPlosSech.SetVArray "asNSech", oLoadedPlosSech.GetVArray("asNSech")
      oPlosSech.SetVArray "aiLenSech", oLoadedPlosSech.GetVArray("aiLenSech")
      oPlosSech.SetVArray "aiKolSech", oLoadedPlosSech.GetVArray("aiKolSech")
      oPlosSech.SetVArray "aiKolKarInSech", oLoadedPlosSech.GetVArray("aiKolKarInSech")
      oPlosSech.SetVArray "aiShagVerh", oLoadedPlosSech.GetVArray("aiShagVerh")
      oPlosSech.SetVArray "aiDiamVerh", oLoadedPlosSech.GetVArray("aiDiamVerh")
      oPlosSech.SetVArray "asKlassVerh", oLoadedPlosSech.GetVArray("asKlassVerh")
      oPlosSech.SetVArray "asGOSTVerh", oLoadedPlosSech.GetVArray("asGOSTVerh")
      oPlosSech.SetVArray "aiShagNiz", oLoadedPlosSech.GetVArray("aiShagNiz")
      oPlosSech.SetVArray "aiDiamNiz", oLoadedPlosSech.GetVArray("aiDiamNiz")
      oPlosSech.SetVArray "asKlassNiz", oLoadedPlosSech.GetVArray("asKlassNiz")
      oPlosSech.SetVArray "asGOSTNiz", oLoadedPlosSech.GetVArray("asGOSTNiz")
      oPlosSech.iCountSech = oLoadedPlosSech.iCountSech
    End If
  Next
  
  'обновляем список в листвиевере
  'заполняем листвиевер плоских.каркасов
  FormSpecRost.ListViewPlosKar.ListItems.Clear
  For Each oKar In pcolClPlosKar
    'если при обработке имени каркаса возникли ошибки то ставим крест
    If oKar.strError = "" Then
      If oKar.bolObrabotan = True Then
        Set oListItem = FormSpecRost.ListViewPlosKar.ListItems.Add(, , oKar.strFirstName, , 1)
      Else
        Set oListItem = FormSpecRost.ListViewPlosKar.ListItems.Add(, , oKar.strFirstName)
      End If
    Else
      Set oListItem = FormSpecRost.ListViewPlosKar.ListItems.Add(, , oKar.strFirstName, , 2)
    End If
    oListItem.SubItems(1) = oKar.intKolKar
    oListItem.SubItems(2) = oKar.strMarkaKPlos
  Next
  
End Function

Public Function GetSetkaFromTXTString(sTxtString As String) As clSetky
  'возвращает объект сетки по данным из строки
  Dim sValue As String
  Dim iValue As Integer
  
  Set GetSetkaFromTXTString = New clSetky
  
  iValue = InStr(sTxtString, ";")
  If iValue <> 0 Then
    GetSetkaFromTXTString.psBlName = Left(sTxtString, iValue - 1)
    sTxtString = Right(sTxtString, Len(sTxtString) - iValue)
  Else
    Set GetSetkaFromTXTString = Nothing
    Exit Function
  End If
  iValue = InStr(sTxtString, ";")
  If iValue <> 0 Then
    GetSetkaFromTXTString.piShagVertSter = Val(Left(sTxtString, iValue - 1))
    sTxtString = Right(sTxtString, Len(sTxtString) - iValue)
  Else
    Set GetSetkaFromTXTString = Nothing
    Exit Function
  End If
  iValue = InStr(sTxtString, ";")
  If iValue <> 0 Then
    GetSetkaFromTXTString.piShagHorSter = Val(Left(sTxtString, iValue - 1))
    sTxtString = Right(sTxtString, Len(sTxtString) - iValue)
  Else
    Set GetSetkaFromTXTString = Nothing
    Exit Function
  End If
  iValue = InStr(sTxtString, ";")
  If iValue <> 0 Then
    GetSetkaFromTXTString.piKolShagovHoris = Val(Left(sTxtString, iValue - 1))
    sTxtString = Right(sTxtString, Len(sTxtString) - iValue)
  Else
    Set GetSetkaFromTXTString = Nothing
    Exit Function
  End If
  iValue = InStr(sTxtString, ";")
  If iValue <> 0 Then
    GetSetkaFromTXTString.piKolShagovVertik = Val(Left(sTxtString, iValue - 1))
    sTxtString = Right(sTxtString, Len(sTxtString) - iValue)
  Else
    Set GetSetkaFromTXTString = Nothing
    Exit Function
  End If
  iValue = InStr(sTxtString, ";")
  If iValue <> 0 Then
    GetSetkaFromTXTString.piDiamVertSter = Val(Left(sTxtString, iValue - 1))
    sTxtString = Right(sTxtString, Len(sTxtString) - iValue)
  Else
    Set GetSetkaFromTXTString = Nothing
    Exit Function
  End If
  iValue = InStr(sTxtString, ";")
  If iValue <> 0 Then
    GetSetkaFromTXTString.piDiamHorSter = Val(Left(sTxtString, iValue - 1))
    sTxtString = Right(sTxtString, Len(sTxtString) - iValue)
  Else
    Set GetSetkaFromTXTString = Nothing
    Exit Function
  End If
  iValue = InStr(sTxtString, ";")
  If iValue <> 0 Then
    GetSetkaFromTXTString.psKlassVertSter = Left(sTxtString, iValue - 1)
    sTxtString = Right(sTxtString, Len(sTxtString) - iValue)
  Else
    Set GetSetkaFromTXTString = Nothing
    Exit Function
  End If
  iValue = InStr(sTxtString, ";")
  If iValue <> 0 Then
    GetSetkaFromTXTString.psKlassHorSter = Left(sTxtString, iValue - 1)
    sTxtString = Right(sTxtString, Len(sTxtString) - iValue)
  Else
    Set GetSetkaFromTXTString = Nothing
    Exit Function
  End If
  iValue = InStr(sTxtString, ";")
  If iValue <> 0 Then
    GetSetkaFromTXTString.psGOSTVertSter = Left(sTxtString, iValue - 1)
    sTxtString = Right(sTxtString, Len(sTxtString) - iValue)
  Else
    Set GetSetkaFromTXTString = Nothing
    Exit Function
  End If
  iValue = InStr(sTxtString, ";")
  If iValue <> 0 Then
    GetSetkaFromTXTString.psGOSTHorSter = Left(sTxtString, iValue - 1)
    sTxtString = Right(sTxtString, Len(sTxtString) - iValue)
  Else
    Set GetSetkaFromTXTString = Nothing
    Exit Function
  End If
  iValue = InStr(sTxtString, ";")
  If iValue <> 0 Then
    GetSetkaFromTXTString.pbDopSter = Left(sTxtString, iValue - 1)
    sTxtString = Right(sTxtString, Len(sTxtString) - iValue)
  Else
    Set GetSetkaFromTXTString = Nothing
    Exit Function
  End If
  
  If GetSetkaFromTXTString.pbDopSter = True Then
    iValue = InStr(sTxtString, ";")
    If iValue <> 0 Then
      GetSetkaFromTXTString.piDiamDopSter = Val(Left(sTxtString, iValue - 1))
      sTxtString = Right(sTxtString, Len(sTxtString) - iValue)
    Else
      Set GetSetkaFromTXTString = Nothing
      Exit Function
    End If
    iValue = InStr(sTxtString, ";")
    If iValue <> 0 Then
      GetSetkaFromTXTString.piKolDopSter = Val(Left(sTxtString, iValue - 1))
      sTxtString = Right(sTxtString, Len(sTxtString) - iValue)
    Else
      Set GetSetkaFromTXTString = Nothing
      Exit Function
    End If
    iValue = InStr(sTxtString, ";")
    If iValue <> 0 Then
      GetSetkaFromTXTString.psKlassDopSter = Left(sTxtString, iValue - 1)
      sTxtString = Right(sTxtString, Len(sTxtString) - iValue)
    Else
      Set GetSetkaFromTXTString = Nothing
      Exit Function
    End If
    iValue = InStr(sTxtString, ";")
    If iValue <> 0 Then
      GetSetkaFromTXTString.psGOSTDopSter = Left(sTxtString, iValue - 1)
      sTxtString = Right(sTxtString, Len(sTxtString) - iValue)
    Else
      Set GetSetkaFromTXTString = Nothing
      Exit Function
    End If
  End If
End Function

Public Function GetPerepadyFromTXTString(sTxtString As String)
  'заполнение листвиевера пенрепадов по данным из строки
  Dim sValue As String
  Dim iValue As Integer
  Dim i As Integer
  Dim oListItem As ListItem
  Dim oListItemVal As ListItem
  
  iValue = InStr(sTxtString, ";")
  
  If iValue <> 0 Then
    sValue = Left(sTxtString, iValue - 1)
    Set oListItem = FormSpecRost.ListViewPerepady.ListItems.Add(, , sValue)
    sTxtString = Right(sTxtString, Len(sTxtString) - iValue)
  Else
    Exit Function
  End If
  
  For i = 1 To 17
    iValue = InStr(sTxtString, ";")
    If iValue <> 0 Then
      oListItem.SubItems(i) = Left(sTxtString, iValue - 1)
      sTxtString = Right(sTxtString, Len(sTxtString) - iValue)
    Else
      FormSpecRost.ListViewPerepady.ListItems.Remove oListItem.index
      Exit Function
    End If
  Next

End Function

Public Function GetDopStergFromTXTString(sTxtString As String) As clDopStergen
  'возвращает объект доп.стержня по данным из строки
  Dim sValue As String
  Dim iValue As Integer
  
  Set GetDopStergFromTXTString = New clDopStergen
  
  iValue = InStr(sTxtString, ";")
  If iValue <> 0 Then
    GetDopStergFromTXTString.sNaimenovanie = Left(sTxtString, iValue - 1)
    sTxtString = Right(sTxtString, Len(sTxtString) - iValue)
  Else
    Set GetDopStergFromTXTString = Nothing
    Exit Function
  End If
  iValue = InStr(sTxtString, ";")
  If iValue <> 0 Then
    GetDopStergFromTXTString.iPoz = Val(Left(sTxtString, iValue - 1))
    sTxtString = Right(sTxtString, Len(sTxtString) - iValue)
  Else
    Set GetDopStergFromTXTString = Nothing
    Exit Function
  End If
End Function

Public Function PrimLoadedDopStergny()
  'применение загруженных объектов доп.стержней к коллекции доп.стержней
  Dim oDopSterLoaded As clDopStergen
  Dim oDopSter As clDopStergen
  Dim oListItem As ListItem
  
  For Each oDopSterLoaded In pcolLoadedDopSterg
On Error Resume Next
    Set oDopSter = pcolClDopStergny(oDopSterLoaded.sNaimenovanie)
    If Err Then
On Error GoTo 0
      'нет такого стержня
    Else
      'применяем параматры
      oDopSter.iPoz = oDopSterLoaded.iPoz
      oDopSter.bolObrabotan = True
    End If
  Next
  
  'обновляем список в листвиевера доп.стержней
  FormSpecRost.ListViewDopSter.ListItems.Clear
  For Each oDopSter In pcolClDopStergny
    'если при обработке имени доп.стержня возникли ошибки то ставим крест
    If oDopSter.sError = "" Then
      If oDopSter.bolObrabotan = False Then
        Set oListItem = FormSpecRost.ListViewDopSter.ListItems.Add(, , oDopSter.sNaimenovanie)
      Else
        Set oListItem = FormSpecRost.ListViewDopSter.ListItems.Add(, , oDopSter.sNaimenovanie, , 1)
      End If
    Else
      Set oListItem = FormSpecRost.ListViewDopSter.ListItems.Add(, , oDopSter.sNaimenovanie, , 2)
    End If
    oListItem.ListSubItems.Add , , oDopSter.iKolvo
  Next
  
  
End Function

Public Function PrimLoadedSetky()
  'применение загруженных объектов сеток
  Dim oSetkaLoaded As clSetky
  Dim oSetka As clSetky
  Dim oListItem As ListItem
  
  For Each oSetkaLoaded In pcolLoadedSetky
On Error Resume Next
    Set oSetka = pcolClSetky(oSetkaLoaded.psBlName)
    If Err Then
On Error GoTo 0
      'нет такого стержня
    Else
      'применяем параматры
      oSetka.piShagVertSter = oSetkaLoaded.piShagVertSter
      oSetka.piShagHorSter = oSetkaLoaded.piShagHorSter
      oSetka.piKolShagovHoris = oSetkaLoaded.piKolShagovHoris
      oSetka.piKolShagovVertik = oSetkaLoaded.piKolShagovVertik
      oSetka.piDiamVertSter = oSetkaLoaded.piDiamVertSter
      oSetka.piDiamHorSter = oSetkaLoaded.piDiamHorSter
      oSetka.psKlassVertSter = oSetkaLoaded.psKlassVertSter
      oSetka.psKlassHorSter = oSetkaLoaded.psKlassHorSter
      oSetka.psGOSTVertSter = oSetkaLoaded.psGOSTVertSter
      oSetka.psGOSTHorSter = oSetkaLoaded.psGOSTHorSter
      oSetka.pbDopSter = oSetkaLoaded.pbDopSter
      If oSetka.pbDopSter = True Then
        oSetka.piDiamDopSter = oSetkaLoaded.piDiamDopSter
        oSetka.piLenDopSter = oSetkaLoaded.piLenDopSter
        oSetka.piKolDopSter = oSetkaLoaded.piKolDopSter
        oSetka.psKlassDopSter = oSetkaLoaded.psKlassDopSter
        oSetka.psGOSTDopSter = oSetkaLoaded.psGOSTDopSter
      End If
    End If
    oSetka.pbObrab = True
  Next
  
  'заполняем листвиевер сеток
  FormSpecRost.ListViewSetky.ListItems.Clear
  For Each oSetka In pcolClSetky
    'если при обработке имени возникли ошибки то ставим крест
    If oSetka.psError = "" Then
      If oSetka.pbObrab = False Then
        Set oListItem = FormSpecRost.ListViewSetky.ListItems.Add(, , oSetka.psBlName)
      Else
        Set oListItem = FormSpecRost.ListViewSetky.ListItems.Add(, , oSetka.psBlName, , 1)
      End If
    Else
      Set oListItem = FormSpecRost.ListViewSetky.ListItems.Add(, , oSetka.psBlName, , 2)
    End If
    oListItem.ListSubItems.Add , , oSetka.piKolvoBl
  Next
  
End Function

Public Function ProvBolDNear13KarInCol(colKar As Collection, iCountOstalos As Integer) As Boolean
  'проверяем есть ли в ближайших 13 каркасах "д" (столько каркасов на одном листе)
  Dim iCountStart As Integer
  Dim i As Integer
  
  iCountStart = colKar.Count - (iCountOstalos - 1)
  
  On Error GoTo HasError
  
  For i = iCountStart To iCountStart + 12
    If colKar(i).bolD = True Then
      ProvBolDNear13KarInCol = True
      Exit Function
    End If
  Next

Exit Function
HasError:
  'недопустимый индекс в коллекции
End Function


'**********************
'**********************
'Таблица - шаблон - форма для заполнения параметров каркасов и других элементов ростверка
'**********************
'**********************
Public Function FormaForDopParam()
   Dim colBlockList1 As New Collection
   Dim objKarkas As clKarkas
   Dim strNameKarkasa As String
   Dim objListItem As ListItem
   Dim objAcadObject As AcadObject
   Dim objTabl As AcadTable
   Dim intRow As Integer
   Dim intValue As Integer
   Dim strFormaFullName As String
   Dim strValue As String
     
      If pbolObrabProsKar = False Then
         'процедура обработки блоков пространственных каркасов из коллеции выбранных блоков каркасов
         Functions.ObrabProsKar
      End If
    
'      sVkladka = "Плоские каркасы"
      If pbolObrabPlosKar = False Then
        Functions.ObrabPlosKar
      End If
    
'      sVkladka = "Сетки"
      If pbolObrabSetok = False Then
        Functions.ObrabSetok
      End If
      
'**** Cортируем коллекцию colBlockList *******************************************
   
   
   
'**** Конец сортируем коллекцию colBlockList *******************************************
   
'копируем форму в папку с проектом
   'путь к папке с чертежами заготовок таблиц
    strValue = psMacroFolder & "\Таблицы\Форма.dwg"
    
    'полный путь с именем сохраняемого файла Форма.dwg в проекте
    'strFormaFullName = strProektPapkaPath & "\" & "Форма-" & strPolnShifrProekta & ".dwg"
    'копируем
    'FileCopy strValue, strFormaFullName
    
   'открываем
   Dim oDocForma As AcadDocument
   
   Set oDocForma = Documents.Open(strValue, True)
   
   'находим таблицу
   Dim bYesTable As Boolean
   Dim oToCopy(0) As Object
   For Each objAcadObject In oDocForma.ModelSpace
      If objAcadObject.ObjectName = "AcDbTable" Then
         Set oToCopy(0) = objAcadObject
         bYesTable = True
         Exit For
      End If
   Next objAcadObject
   
   If bYesTable = False Then
      Call MsgBox("Таблица не найдена в файле шаблона ...\Макросы\Таблицы\Форма.dwg", vbOKOnly, pcsVBProjectName)
      Exit Function
   End If
   
   'Копируем таблицу в новый Чертеж1
   Dim oNewDocForma As AcadDocument
   Set oNewDocForma = Documents.Add
   
   Dim oCopys As Variant
   
   oCopys = oDocForma.CopyObjects(oToCopy, oNewDocForma.ModelSpace)
   
   'может быть ошибка при закрытии файла. Причина неизвестна.
   'можно пропустиить эту ошибку и ручками закрыть файл шаблона формы.
   On Error Resume Next
   oDocForma.Close
   On Error GoTo 0
   
   Set objTabl = oCopys(0)
  
  objTabl.RegenerateTableSuppressed = True
  
  'вводим дату
  
  objTabl.SetCellValue 0, 0, "Данные (доп.параметры) для повторного расчета спецификаций, получены - " & FormatDateTime(Now, vbShortDate)
  
  'добавляем шифр ' - шифр пока неизвестен
   'intRow = 1
   'objTabl.SetCellValue intRow, 0, "Шифр проекта: " & strPolnShifrProekta 'шифр
  
  intRow = 5 'в этой строке значения по умолчанию
  'заполняем таблицу
   intValue = 0 'входящее значение
   For Each objKarkas In pcolClProsKar
       
      If objKarkas.bolP = True Then 'отбираем простр.каркасы
         intRow = intRow + 1
         objTabl.InsertRows intRow, 6, 1 'вставляем строчку
         intValue = intValue + 1 'номер каркаса по порядку
         objTabl.SetCellValue intRow, 0, intValue
         If FormSpecRost.CheckBoxMarkaK.Value = True Then
            objTabl.SetCellValue intRow, 1, objKarkas.Name & " (" & objKarkas.strMarkaK & ")"
         Else
            objTabl.SetCellValue intRow, 1, objKarkas.Name
         End If
         objTabl.SetCellAlignment intRow, 1, acMiddleLeft  'выравнваем влево имя каркаса
         objTabl.SetCellValue intRow, 2, objKarkas.intKolKar
      End If
      
   Next objKarkas
   
'   Dim bolDaNet As Boolean
'   bolDaNet = False 'уст нач знач
'   'заполняем плоские каркасы
'   'проверяем есть ли плоские каркасы в коллекции
'   For Each objKarkas In pcolBlKar
'      If objKarkas.bolP = False Then 'отбираем плоские.каркасы
'         bolDaNet = True
'         Exit For
'      End If
'   Next objKarkas

   If pcolClPlosKar.Count <> 0 Then 'если есть плоские каркасы
      'делаем шапку для плос каркасов
      intRow = intRow + 1
      objTabl.InsertRows intRow, 6, 2 'вставляем 2 строчки
      intRow = intRow + 1
      objTabl.SetCellValue intRow, 0, "№"
      objTabl.SetCellValue intRow, 1, "Плоские карасы" 'в первый столбец
      objTabl.SetCellValue intRow, 2, "Кол-во каркасов"
      objTabl.SetCellValue intRow, 3, "Номер сеч."
      objTabl.SetCellValue intRow, 4, "Кол. сечений"
      objTabl.SetCellValue intRow, 5, "Кол. в сечении"
      
      intValue = 0 'входящее значение
      For Each objKarkas In pcolClPlosKar
         If objKarkas.bolP = False Then 'отбираем плоские.каркасы
            intRow = intRow + 1
            objTabl.InsertRows intRow, 6, 1 'вставляем cтрочку
            intValue = intValue + 1 'номер каркаса по порядку
            objTabl.SetCellValue intRow, 0, intValue
            objTabl.SetCellValue intRow, 1, objKarkas.Name 'в первый столбец - имя сетки "Сетка С1(шт.2)"
            If FormSpecRost.CheckBoxMarkaK.Value = True Then
               objTabl.SetCellValue intRow, 1, objKarkas.Name & " (" & objKarkas.strMarkaK & ")"
            Else
               objTabl.SetCellValue intRow, 1, objKarkas.Name
            End If
            objTabl.SetCellAlignment intRow, 1, acMiddleLeft 'выавнваем влево имя каркаса
            objTabl.SetCellValue intRow, 2, objKarkas.intKolKar
         End If
      Next objKarkas
   End If
   
   Dim objSetka As clSetky
   
   'сетки добавлять ???
   If pcolClSetky.Count <> 0 Then
      'делаем заголовок для сеток
      intRow = intRow + 1
      objTabl.InsertRows intRow, 6, 2 'вставляем 2 строчки
      intRow = intRow + 1
      objTabl.SetCellValue intRow, 1, "Сетки" 'в первый столбец
      objTabl.SetCellValue intRow, 2, "Кол-во"
      objTabl.SetCellValue intRow, 3, "Диам"
      objTabl.SetCellValue intRow, 4, "ШагГ"
      objTabl.SetCellValue intRow, 5, "КолГ"
      objTabl.SetCellValue intRow, 6, "ШагВ"
      objTabl.SetCellValue intRow, 7, "КолВ"
      
      intValue = 0 'входящее значение
      For Each objSetka In pcolClSetky
         intRow = intRow + 1
         objTabl.InsertRows intRow, 6, 1 'вставляем cтрочку
         intValue = intValue + 1 'номер каркаса по порядку
         objTabl.SetCellValue intRow, 0, intValue
         objTabl.SetCellValue intRow, 1, objSetka.Name 'в первый столбец - имя сетки "Сетка С1(шт.2)"
         objTabl.SetCellAlignment intRow, 1, acMiddleLeft 'выавнваем влево имя каркаса
         objTabl.SetCellValue intRow, 2, objSetka.piKolSetok
      Next
   End If
   
   objTabl.RegenerateTableSuppressed = False
   
   'ZoomAll
   Dim minExt As Variant
   Dim maxExt As Variant
   objTabl.GetBoundingBox minExt, maxExt
   ZoomWindow minExt, maxExt
   'ZoomCenter objTabl.InsertionPoint, 150
   
   'End ' конец программы, когда заполните форму приходите
   
End Function

'Возвращает путь к папке из полного пути у файлу
Public Function GetFolderPathFromFileFullPath(sFullPath) As String
  
  Dim iDec As Integer
  
  iDec = InStrRev(sFullPath, "\")
  
  GetFolderPathFromFileFullPath = Left(sFullPath, iDec - 1)
  
End Function

'Строка класса арматуры и марки стали для Ведомости расхода стали
Public Function GetKlassAndMarkaStali(sKlassArm) As String
  
  Dim sMarkaStali As String
  'ищем текстбокс класса арм для марки стали
  If FormSpecRost.TextBox1KlassArmForMarkaStali = sKlassArm Then
      sMarkaStali = FormSpecRost.TextBox1MarkaStali
  End If
  If FormSpecRost.TextBox2KlassArmForMarkaStali = sKlassArm Then
      sMarkaStali = FormSpecRost.TextBox2MarkaStali
  End If
  If FormSpecRost.TextBox3KlassArmForMarkaStali = sKlassArm Then
      sMarkaStali = FormSpecRost.TextBox3MarkaStali
  End If
  
  If Strings.Len(sMarkaStali) = 0 Then
     GetKlassAndMarkaStali = sKlassArm
  Else
     GetKlassAndMarkaStali = sKlassArm & " (марка стали " & sMarkaStali & ")"
  End If
  
End Function

Public Function ShtampAttrFamilyFill(vExplode As Variant)
   
   'должность1
   vExplode(3).TextString = psShtampPost1
   If Len(psShtampPost1) > 10 Then
      vExplode(3).ScaleFactor = 0.8
   End If
   'фамилия1
   vExplode(4).TextString = GetFamilWithoutInitial(psShtampFam1)
   If Len(vExplode(4).TextString) > 10 Then
      vExplode(4).ScaleFactor = 0.8
   End If
   'должность2
   vExplode(5).TextString = psShtampPost2
   If Len(psShtampPost2) > 10 Then
      vExplode(5).ScaleFactor = 0.8
   End If
   'фамилия2
   vExplode(6).TextString = GetFamilWithoutInitial(psShtampFam2)
   If Len(vExplode(6).TextString) > 10 Then
      vExplode(6).ScaleFactor = 0.8
   End If
   'должность3
   vExplode(7).TextString = psShtampPost3
   If Len(psShtampPost3) > 10 Then
      vExplode(7).ScaleFactor = 0.8
   End If
   'фамилия3
   vExplode(8).TextString = GetFamilWithoutInitial(psShtampFam3)
   If Len(vExplode(8).TextString) > 10 Then
      vExplode(8).ScaleFactor = 0.8
   End If
   'должность4
   vExplode(9).TextString = psShtampPost4
   If Len(psShtampPost4) > 10 Then
      vExplode(9).ScaleFactor = 0.8
   End If
   'фамилия4
   vExplode(10).TextString = GetFamilWithoutInitial(psShtampFam4)
   If Len(vExplode(10).TextString) > 10 Then
      vExplode(10).ScaleFactor = 0.8
   End If
   'должность5
   vExplode(11).TextString = psShtampPost5
   If Len(psShtampPost5) > 10 Then
      vExplode(11).ScaleFactor = 0.8
   End If
   'фамилия5
   vExplode(12).TextString = GetFamilWithoutInitial(psShtampFam5)
   If Len(vExplode(12).TextString) > 10 Then
      vExplode(12).ScaleFactor = 0.8
   End If
   
End Function

Private Function DefinePostAndFamForSthampAndTitul()
   'опркделить должности и фамилии для штампов и титульного листа
   
   psTitulPost1 = ""
   psTitulPost2 = ""
   psTitulPost3 = ""
   psTitulFam1 = ""
   psTitulFam2 = ""
   psTitulFam3 = ""
   psShtampPost1 = ""
   psShtampPost2 = ""
   psShtampPost3 = ""
   psShtampPost4 = ""
   psShtampPost5 = ""
   psShtampPost6 = ""
   psShtampFam1 = ""
   psShtampFam2 = ""
   psShtampFam3 = ""
   psShtampFam4 = ""
   psShtampFam5 = ""
   psShtampFam6 = ""
   
   'должности и фамилии для титула
   If FormSpecRost.cbShtampTitul1 = True Then
      psTitulPost1 = FormSpecRost.TextBoxPost1
      psTitulFam1 = FormSpecRost.TextBoxFam1
      If FormSpecRost.cbShtampTitul2 = True Then
         psTitulPost2 = FormSpecRost.TextBoxPost2
         psTitulFam2 = FormSpecRost.TextBoxFam2
         If FormSpecRost.cbShtampTitul3 = True Then
            psTitulPost3 = FormSpecRost.TextBoxPost3
            psTitulFam3 = FormSpecRost.TextBoxFam3
         End If
      End If
   Else
      If FormSpecRost.cbShtampTitul2 = True Then
         psTitulPost1 = FormSpecRost.TextBoxPost1
         psTitulFam1 = FormSpecRost.TextBoxFam1
         If FormSpecRost.cbShtampTitul3 = True Then
            psTitulPost2 = FormSpecRost.TextBoxPost2
            psTitulFam2 = FormSpecRost.TextBoxFam2
         End If
      Else
         If FormSpecRost.cbShtampTitul3 = True Then
            psTitulPost1 = FormSpecRost.TextBoxPost1
            psTitulFam1 = FormSpecRost.TextBoxFam1
         End If
      End If
   End If
   
   'определение номеров галок
   Dim i As Integer
   Dim index As Integer
   Dim chekBoxTrueIndex(0 To 4) As Integer
   For i = 0 To 5
      If FormSpecRost.FrameShtampShtamp("cbShtamp" + CStr(i + 1)).Value = True Then
         chekBoxTrueIndex(index) = i + 1
         index = index + 1
      End If
   Next
   'запись должностей и фамилий
   Dim tb As TextBox
   If chekBoxTrueIndex(0) <> 0 Then
      Set tb = FormSpecRost("TextBoxPost" + CStr(chekBoxTrueIndex(0)))
      psShtampPost1 = tb.Text
      Set tb = FormSpecRost("TextBoxFam" + CStr(chekBoxTrueIndex(0)))
      psShtampFam1 = tb.Text
      If chekBoxTrueIndex(1) <> 0 Then
         Set tb = FormSpecRost("TextBoxPost" + CStr(chekBoxTrueIndex(1)))
         psShtampPost2 = tb.Text
         Set tb = FormSpecRost("TextBoxFam" + CStr(chekBoxTrueIndex(1)))
         psShtampFam2 = tb.Text
         If chekBoxTrueIndex(2) <> 0 Then
            Set tb = FormSpecRost("TextBoxPost" + CStr(chekBoxTrueIndex(2)))
            psShtampPost3 = tb.Text
            Set tb = FormSpecRost("TextBoxFam" + CStr(chekBoxTrueIndex(2)))
            psShtampFam3 = tb.Text
            If chekBoxTrueIndex(3) <> 0 Then
               Set tb = FormSpecRost("TextBoxPost" + CStr(chekBoxTrueIndex(3)))
               psShtampPost4 = tb.Text
               Set tb = FormSpecRost("TextBoxFam" + CStr(chekBoxTrueIndex(3)))
               psShtampFam4 = tb.Text
               If chekBoxTrueIndex(4) <> 0 Then
                  Set tb = FormSpecRost("TextBoxPost" + CStr(chekBoxTrueIndex(4)))
                  psShtampPost5 = tb.Text
                  Set tb = FormSpecRost("TextBoxFam" + CStr(chekBoxTrueIndex(4)))
                  psShtampFam5 = tb.Text
               End If
            End If
         End If
      End If
   End If
   
End Function

Public Function VerifyCheckBoxForShtamp()
   'проверка кол-ва галок на вкладке Исх данных для Штампов
   Dim i As Integer
   Dim num As Integer
   Dim ctrl As Control
   Dim maxnum As Integer 'максимальное кол фамилий (начиная с 1)
   maxnum = 5
   
   For Each ctrl In FormSpecRost.FrameShtampShtamp.Controls
      If TypeOf ctrl Is CheckBox Then
         If ctrl.Value = True Then
            num = num + 1
         End If
      End If
   Next
   
   If num = maxnum Then
      For Each ctrl In FormSpecRost.FrameShtampShtamp.Controls
         If TypeOf ctrl Is CheckBox Then
            If ctrl.Value = False Then
               ctrl.Enabled = False
            End If
         End If
      Next
   End If
   If num < maxnum Then
      For Each ctrl In FormSpecRost.FrameShtampShtamp.Controls
         If TypeOf ctrl Is CheckBox Then
            If ctrl.Value = False Then
               ctrl.Enabled = True
            End If
         End If
      Next
   End If
   If num > maxnum Then
      For Each ctrl In FormSpecRost.FrameShtampShtamp.Controls
         If TypeOf ctrl Is CheckBox Then
            If ctrl.Value = True Then
               ctrl.Enabled = True
               ctrl.Value = False
            End If
         End If
      Next
   End If
   
End Function

Public Function ReplaceInvalidCharsForFileName(sTextForName As String) As String
   Dim sRes As String
   sRes = VBA.Strings.Replace(sTextForName, "\", "-")
   sRes = VBA.Strings.Replace(sRes, "/", "-")
   sRes = VBA.Strings.Replace(sRes, ":", "-")
   sRes = VBA.Strings.Replace(sRes, "*", "-")
   sRes = VBA.Strings.Replace(sRes, "?", "-")
   sRes = VBA.Strings.Replace(sRes, "<", "-")
   sRes = VBA.Strings.Replace(sRes, ">", "-")
   sRes = VBA.Strings.Replace(sRes, "|", "-")
   sRes = VBA.Strings.Replace(sRes, ";", "-")
   sRes = VBA.Strings.Replace(sRes, ",", "-")
   sRes = VBA.Strings.Replace(sRes, "=", "-")
   sRes = VBA.Strings.Replace(sRes, "'", "-")
   ReplaceInvalidCharsForFileName = sRes
End Function

Attribute VB_Name = "Main"
Option Explicit

  Public Const pcsVBProjectName As String = "SpecRost2"
  Public psMacroFolder As String 'каталог макросов
  Public psUserName As String 'фамилия пользователя
  Public oShifr As clShifr
'  Public Const pcsSelSetName As String = pcsVBProjectName
  Public pdocSpecRost As AcadDocument 'расчитываемый чертеж
  
  'объект для хранения настроек
  Public pclOptions As clOptions
  
  'коллекции выбранных блоков
  Public pcolBlKar As New Collection
  Public pcolBlSetky As New Collection
  Public pcolBlDopSterg As New Collection
  Public pcolNeoprBlock As New Collection
  
  'коллекции блоков с ошибками (для формы FormaProverky)
  Public pcolBlDublicates As New Collection
  Public pcolBlOnFreezeLayer As New Collection
  
  'коллекции объектов для спецификации
  Public pcolClProsKar As New Collection 'коллекция объектов класса clKarkas простран каркасов
  Public pcolClPlosKar As New Collection 'коллекция объектов класса clKarkas плоских каркасов
  Public pcolAllPlosKar As New Collection 'коллекция плоских каркасов (из простр +плоских)
  Public pcolClPlosKarSech As New Collection 'коллекция параметров сечений плоских каркасов
  Public pcolClDopStergny As New Collection 'коллекция объектов доп.стержней
  Public pcolAllDopStergny As New Collection 'объединенная коллекция доп.стержней
  Public pcolClSetky As New Collection 'коллекция объектов сеток по названиям блоков
  Public pcolClShpilek As New Collection 'коллекция шпилек
  Public pcolSetkyMarka As New Collection 'коллекция сеток по маркам
  Public pcolArmKlass As New Collection 'коллекция выборки стали
  'признаки для определения обработаны ли вкладки после Выбора блоков
  Public pbolObrabProsKar As Boolean
  Public pbolObrabPlosKar As Boolean
  Public pbolObrabAttrubutov As Boolean 'обработка исходных данных
  Public pbolObrabSetok As Boolean
  Public pbolObraDopSter As Boolean
  Public pbolObrabPerepadov As Boolean
  Public pbolObrabAtributov As Boolean ' обработаны ли исходные данные проекта
  
  Public psShifr As String
  Public pcolSoderg As Collection  'коллекция содержания листов
  
  Public psFolderSpecPath As String 'путь к папке со спецификациями
  Public psFilePlosPath As String 'файл спец-ии плоских каркасов
  Public psFileProsPath As String 'файл спец-ии простр.каркасов
  Public psFileSpecElemPath As String 'файл спец-ии элементов ростверка
  Public psFileVedomStalyPath As String 'файл ведомости расхода стали
  Public psFileSodergPath As String 'файл содержания
  Public psFileTitPath As String 'файл обложек
  Public psFileSaveRaschetPath As String 'файл для сохранения расчета
  
  Public psBlSpecElem As String 'имя для блока спецификации элементов ростверка
  Public psBlVedStaly As String 'имя для блока ведомости расхода стали
  
  'коллекции для загруочных объектов
  Public pcolLoadedProsKar As New Collection
  Public pcolLoadedPlosKar As New Collection
  Public pcolLoadedPlosKarSech As New Collection
  Public pcolLoadedSetky As New Collection
  Public pcolLoadedDopSterg As New Collection

Public Sub Main()

  On Error GoTo HasError
    
  'проверка версии акада
  Dim intVer As Integer
  intVer = Val(Version)
  If intVer <> 17 Then
    Dim sQuest As String
    sQuest = "Программа написана для AutoCAD2008." & vbCr & _
        "В других версиях возможна некорректная работа." & vbCr & _
        "Продолжить?"
    If MsgBox(sQuest, vbYesNo + vbExclamation, pcsVBProjectName) = vbNo Then Exit Sub
  End If
  
  psMacroFolder = Functions.GetMacroFolder
  psUserName = Functions.GetUserFamily
  
  'очистка SelectionSets текущего чертежа
  Functions.ClearSelSets
  
  'отображение формы
  FormSpecRost.Show

Exit Sub
HasError:
  MsgBox Err.Description, vbCritical, pcsVBProjectName
  
End Sub

Attribute VB_Name = "OpenFileDialog"
Option Explicit

'Диалог выбора файла

'Взято с форума DWG.RU
'тема: Как открыть диалог Open или Save на VBA под AutoCAD
'автор: trir

'Пример вызова диалога выбора файла
'sFile = OpenFile("Чертёж", "*.dwg", "c:\")

Public Type OpenFileName
lStructSize As Long
hwndOwner As Long
hInstance As Long
lpstrFilter As String
lpstrCustomFilter As String
nMaxCustFilter As Long
nFilterIndex As Long
lpstrFile As String
nMaxFile As Long
lpstrFileTitle As String
nMaxFileTitle As Long
lpstrInitialDir As String
lpstrTitle As String
flags As Long
nFileOffset As Integer
nFileExtension As Integer
lpstrDefExt As String
lCustData As Long
lpfnHook As Long
lpTemplateName As String
End Type

Public Declare Function GetOpenFileName Lib "comdlg32.dll" Alias "GetOpenFileNameA" _
(pOpenfilename As OpenFileName) As Long

Public Function OpenFile(Filter As String, Extention As String, Optional Directory As String) As String
Dim strTemp As String
Dim OpenFileName As OpenFileName
With OpenFileName
.lStructSize = Len(OpenFileName)
.hwndOwner = ThisDrawing.HWND
.lpstrFilter = Filter & " (" & Extention & ")" & Chr$(0) & Extention & Chr$(0)
.lpstrFile = Space$(254)
.nMaxFile = 255
.lpstrFileTitle = Space$(254)
.nMaxFileTitle = 255
.lpstrInitialDir = Directory
.lpstrTitle = "Выбор Файла"
.flags = 0
If GetOpenFileName(OpenFileName) Then
strTemp = (Trim(.lpstrFile))
OpenFile = Mid(strTemp, 1, Len(strTemp) - 1)
End If
End With
End Function

Attribute VB_Name = "WinAPI"
Option Explicit

Private Declare Function GetComputerName Lib "kernel32" Alias "GetComputerNameA" (ByVal lpBuffer As String, nSize As Long) As Long
Private Declare Function GetUserName Lib "advapi32.dll" Alias "GetUserNameA" _
        (ByVal lpBuffer As String, nSize As Long) As Long

'функции получения имени компьютера и имени пользователя
'v_1.0.0 990630
Public Function ComputerName() As String
   Dim a As String * 40
   Dim nSize As Long
   nSize = 40
   Call GetComputerName(a, nSize)
   ComputerName = StrZ(a)
End Function
'v_1.0.0 990831
Public Function UserName() As String
Dim a As String * 40
Dim nSize As Long
nSize = 40
   Call GetUserName(a, nSize)
   UserName = StrZ(a)
End Function
'v_1.0.0 990630
Private Function StrZ(par As String) As String
Dim nSize As Long, i As Long, Rez As String
   nSize = Len(par)
   i = InStr(1, par, Chr(0)) - 1
   If i > nSize Then i = nSize
   If i < 0 Then i = nSize
   StrZ = Mid(par, 1, i)
End Function

Attribute VB_Name = "clArmKlas"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public psKlassArm As String
Public colArmKlassDiam As New Collection

Public Sub AddMassaToDiam(iDiam As Integer, dMassa As Double)
  'добавление массы заданного диаметра арматуры
  Dim oArmKlassDiam As clArmKlassDiam
  
  On Error Resume Next
  'проверяем если уже есть такой диаметр то плюсуем массу
  Set oArmKlassDiam = colArmKlassDiam.Item(CStr(iDiam))
  If Err Then
    Err.Clear
    'нет такого, добавляем
    Set oArmKlassDiam = New clArmKlassDiam
    oArmKlassDiam.piDiam = iDiam
    oArmKlassDiam.pdMassa = dMassa
    colArmKlassDiam.Add oArmKlassDiam, CStr(iDiam)
  Else
    'плюсуем массу
    oArmKlassDiam.pdMassa = oArmKlassDiam.pdMassa + dMassa
  End If
  
End Sub

Attribute VB_Name = "clArmKlassDiam"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public piDiam As Integer
Public pdMassa As Double

Attribute VB_Name = "clDopStergen"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'Класс для объектов типа доп.стержни, содержет свойство диаметра и длину стержня этого диаметра
Option Explicit

Public sBlName As String
Public iDiametr As Integer
Public iKolvo As Integer 'общее кол-во стержней
Public iKolShtuk As Integer
Public iLenght As Integer
Public dMassaEd As Double
Public dMassa As Double
Public sKlassArm As String 'A-III
Public sGOSTArm As String 'ГОСТ 5781-82
'Naimenovanie, наименование для спецификации "18-A-III ГОСТ 5781-82, L=1800"
Public sNaimenovanie As String
Public iPoz As Integer 'позиция стержня в спеке (если это блок доп.стерженя на чертеже)
Public sError As String
Public bolObrabotan As Boolean

Public Sub Obrab()
   'по имени доп. стержня в fNameLenght, определяем диаметр, длину и ед. массу
   
   Dim strValue As String
   Dim intValue As Integer
   Dim dMassaPM As Double
   
   dMassaPM = GetMassaDiamPM(iDiametr)
   
   'определяем массу одного стержня, кг
   dMassaEd = dMassaPM * (iLenght / 1000)
   'определяем общую массу
   dMassa = dMassaEd * iKolvo
   
End Sub

Public Sub ObrabBlName(sName As String)
  'обработка блока доп.стержня
  'Доп.стержень18(шт.8)
  
  Dim iValue As Integer
  
  sBlName = sName
  
  'диаметр
  iDiametr = Val(Mid(sBlName, Len(pclOptions.psDopSterConst) + 1))
  'проверяем диаметр
  If Functions.ProvDiamStandard(iDiametr) = False Then
    sError = "Диаметр не стандартный. "
  End If
  
  'длина линии
  iValue = InStr(sBlName, "L")
  iLenght = Val(Mid(sBlName, iValue + 1))
  If iLenght = 0 Then
    sError = sError & "Длина не определена. "
  End If
  
  'кол-во штук
  iValue = InStr(LCase(sBlName), "(шт.")
  If iValue = 0 Then
    iKolShtuk = 1
  Else
    iKolShtuk = Val(Mid(sBlName, iValue + 4))
  End If
  
  'класс арматуры
  sKlassArm = pclOptions.psKlassDopStergDef
  'гост арматуры
  sGOSTArm = pclOptions.psGOSTDopStergDef
  
  'наименование
  sNaimenovanie = iDiametr & "-" & sKlassArm & " " & sGOSTArm & ", L=" & iLenght
  
End Sub

Public Sub ObrabNaimenov()
  'обработка наименования стержня
  
  Dim iValue As Integer
  
  'проверяем диаметр
  If Functions.ProvDiamStandard(iDiametr) = False Then
    sError = "Диаметр не стандартный. "
  End If
  
  'длина
  If iLenght = 0 Then
    sError = sError & "Длина не определена. "
  End If
  
  'класс арматуры
  If sKlassArm = "" Then
    sKlassArm = pclOptions.psKlassDopStergDef
  End If
  'гост арматуры
  If sGOSTArm = "" Then
    sGOSTArm = pclOptions.psGOSTDopStergDef
  End If
  
  'наименование
  sNaimenovanie = iDiametr & "-" & sKlassArm & " " & sGOSTArm & ", L=" & iLenght
  
End Sub

''для сортировки
'Public Property Get Name() As String
'  Name = sNaimenovanie
'End Property

Attribute VB_Name = "clKarkas"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'класс описывающий пространственный каркас

   Public strBlName As String 'входное имя каркаса
   
   'доступные поля
   Public strMarkaK As String 'марка по типу 6ПК1
   Public strMarkaKPlos As String 'марка плос кар по типу К1
   Public strType As String 'тип каркаса КО, КД, К
   Public strError As String 'текст ошибки если она есть
   Public strPrim As String 'примечание (может пригодится)
   Public strFirstName As String 'входное имя каркаса
   Public strPlosKarName As String 'имя плос каркаса (всё! что после П)
   Public bolP As Boolean 'простр.каркас
   Public intN As Integer 'кол-во n
   Public intP As Integer 'кол-во плоских каркасов
   Public intLenRab As Integer 'рабочая длина каркаса = n*150
   Private intLenRabPlusDopShag As Integer 'рабочая длина каркаса с доп шагом если он есть
   Public intKolKar As Integer 'кол-во каркасов (с учетом (шт.2), для плоских каркасов)
   Public sNSech As String 'номер сечения
   Public intLenSech As Integer 'ширина сечения
   Public intHeightRost As Integer 'высота ростверка
   Public bolHeightRostInName As Boolean 'признак заданной высоты ростверка в названии (в скобках) каркаса,  (6)
   Public sShifrProsKar As String 'шифр листа пространственного каркаса
   Public sShifrPlosKar As String 'шифр листа плоского каркаса
   Public bolObrabotan As Boolean 'признак обработки каркаса, галочка (т.е. нажали применить для него)
   Public bolD As Boolean 'признак наличия доп.попер.стержня
   Public intShagDopPopSter As Integer 'шаг доп. поп. стержня
   Public intHvostLeft As Integer 'длина левого хвоста
   Public intHvostRight As Integer 'длина правого хвоста
   Public intCenterVerhArm As Integer 'расст от верха роств до центра верхней продол арм
   Public intCenterNizArm As Integer 'расст от низа роств до центра нижней продол арм
   Public dMassaProsKar As Double 'масса пространственного каркаса
   Public dMassaPlosKar As Double 'масса плоского каркаса
   'продольная арматура
   Public intDiamVerhArm As Integer 'диаметр верх арм
   Public intDiamNizArm As Integer 'диам нижней арм
   Public intLenProdolArm As Integer 'длина продольной арматуры
   Public sKlassVerhArm As String 'класс верхней арматуры ("A-III")
   Public sKlassNizArm As String 'класс нижней арматуры
   Public sGOSTVerhArm As String 'норматив.док. верхней арматуры ("ГОСТ 5781-82")
   Public sGOSTNizArm As String 'норматив.док. нижней арматуры
   Public dMassaEdVerhSter As Double 'масса одного верхнего стержня
   Public dMassaEdNizSter As Double 'масса одного нижнего стержня
   Public sNaimVerhArm As String 'наименование верх арм
   Public sNaimNizArm As String 'наименование нижней арм
   'поперечная арматура
   Public intDiamPopArm As Integer 'диаметр поперечной арм
   Public intLenPopArm As Integer 'длина поперечной арматуры
   Public intShagPopArm As Integer 'шаг поперечной арм
   Public sKlassPopArm As String 'класс поперечной арматуры
   Public sGOSTPopArm As String 'норматив.док. поперечной арматуры
   Public intKolPopSterPlosKar As Integer 'кол-во поперечных стержней в плоском каркасе
   Public dMassaEdPopSter As Double 'масса одного поперечного стержня
   Public sNaimPopArm As String 'наименование поперечного арм
   'связевая арматура
   Public intLenSvyzArm As Integer 'длина связевой арматуры
   Public intDiamSvyzVerhArm As Integer 'диаметр связевой верхней арматуры
   Public intDiamSvyzNizArm As Integer 'диаметр связевой нижней арматуры
   Public intShagSvyzVerhArm As Integer 'шаг связевой верхней арматуры
   Public intShagSvyzNizArm As Integer 'шаг связевой нижней арматуры
   Public intKolSvyzVerhSter As Integer 'кол связевой верхней арматуры
   Public intKolSvyzNizSter As Integer 'кол связевой нижней арматуры
   Public sKlassSvyzVerhArm As String 'класс связевой верхней арматуры
   Public sKlassSvyzNizArm As String 'класс связевой нижней нарматуры
   Public sGOSTSvyzVerhArm As String 'норматив.док. связевой верхней арматуры
   Public sGOSTSvyzNizArm As String 'норматив.док. связевой нижней арматуры
   Public dMassaEdSvyzVerhSter As Double 'масса одного связевого верхнего стержня
   Public dMassaEdSvyzNizSter As Double 'масса одного связевого нижнего стержня
   Public sNaimSvyzNizArm As String 'наименование связевого нижнего арм
   Public sNaimSvyzVerhArm As String 'наименование связевого верхнего арм
   'параметры для усиления (масса будет обрабатываться в классе доп.стержней)
   Public bolUsilenie As Boolean 'признак наличия усиления
   Public intUsLen As Integer 'ширина усиливыаемого сечения
   Public intUsKolKar As Integer 'кол усиливаемых каркасов
   Public intUsDiamVerhArm As Integer 'диаметр верхних усиливающих стержней
   Public intUsDiamNizArm As Integer 'диаметр нижних усиливающих стержней
   Public intUsShagVerhArm As Integer 'шаг верхних усиливающих стержней
   Public intUsShagNizArm As Integer 'шаг нижних усиливающих стержней
   Public sUsKlassVerhArm As String 'класс верхней усиливающей арматуры
   Public sUsKlassNizArm As String 'класс нижней усиливающей арматуры
   Public sUsGOSTVerhArm As String 'норм.док. верхней усиливающей арматуры
   Public sUsGOSTNizArm As String 'норм.док. нижней усиливающей арматуры
   
'имя каркаса для сортировки
Public Property Get Name() As String
  Name = strFirstName
End Property
'Public Property Let Name(ByVal vNewValue As String)
'
'   Dim intValue As Integer
'   Dim strValue As String
'   Dim strNameVal As String
'
'   strBlName = vNewValue
'
'   ObrabName strBlName
'
'   'начальное значение кол-ва каркасов(блоков на чертеже)
'   intKolKar = 1
'
'   'имя блока
'   strBlName = vNewValue
'
'   strFirstName = Functions.GetFirstNameProsKar(strBlName)
   
'   intValue = InStr(strFirstName, "-")
'   'оставшаяся строка до "-"
'   If intValue <> 0 Then
'      strNameVal = Left(strFirstName, intValue - 1)
'   Else
'      'если есть скобки то отбрасываем их пока
'      intValue = InStr(strFirstName, "(")
'      If intValue = 0 Then
'        strNameVal = strFirstName
'      Else
'        strNameVal = Left(strFirstName, intValue - 1)
'      End If
'   End If
'
'   'по полученному имени определяем тип каркаса и все остальное
'
'   'кол-во плоских каркасов ("5П45КД" - 5 плоских каркасиков)
'   intP = Val(strNameVal)
'   'номер П в имени каркаса
'   intValue = InStr(LCase(strNameVal), "п")
'   'имя после П
'   strNameVal = Right(strNameVal, Len(strNameVal) - intValue)
'
'   'определяем раб длину L= n*150
'   intN = Val(strNameVal)
'   intLenRab = intN * 150
'   If intLenRab = 0 Then
'      strError = "Рабочая длина каркаса (n*150) - не определена. "
'      Exit Property
'   End If
'
'   intValue = InStr(LCase(strNameVal), "к")
'   'оставшаяся строка после "к"
'   strNameVal = Right(strNameVal, Len(strNameVal) - intValue)
'
'   'после "к" может стоять или "О","Д", или ничего
'   strValue = LCase(Mid(strNameVal, 1, 1))
'
'   If strValue = "о" Then
'      strType = "КО"
'      strValue = Right(strNameVal, Len(strNameVal) - 1)
'      If Len(strValue) > 1 Then
'         strError = "После КО может быть максимум одна цифра. "
'         Exit Property
'      End If
'   ElseIf strValue = "д" Then
'      strType = "КД"
'      strValue = Right(strNameVal, Len(strNameVal) - 1)
'      If Len(strValue) > 2 Then
'         strError = "После КД может быть максимум две цифры. "
'         Exit Property
'      End If
'   ElseIf strValue = "" Then
'      strType = "К"
'   Else
'      strError = "После К стоит недопустимый символ. "
'   End If
'   'определяем длину хвостов
'   Select Case strType
'      Case "КД"
'         intHvostLeft = ReturnLenHvosta(Val(Left(strValue, 1)))
'         intHvostRight = ReturnLenHvosta(Val(Right(strValue, 1)))
'      Case "КО"
'         intHvostLeft = 20
'         intHvostRight = ReturnLenHvosta(Val(Left(strValue, 1)))
'      Case "К"
'         intHvostLeft = 20
'         intHvostRight = 20
'   End Select
'
'   If intHvostLeft = 0 Or intHvostRight = 0 Then
'      strError = "Длина хвостов не определена. "
'      Exit Property
'   End If
'
'   'длина продольной арматуры
'   intLenProdolArm = intLenRab + intHvostLeft + intHvostRight
'
'   'проверяем то что после "-"
'
'   intValue = InStr(strFirstName, "-")
'   'оставшаяся строка после "-"
'   strNameVal = Right(strFirstName, Len(strFirstName) - intValue)
'   'если есть скобки то отбрасываем их пока
'   intValue = InStr(strNameVal, "(")
'   If intValue <> 0 Then
'      strNameVal = Left(strNameVal, intValue - 1)
'   End If
'
'   If InStr(strNameVal, "д") <> 0 Then
'      bolD = True
'   End If
'
'   intValue = InStr(strNameVal, "в")
'   If intValue = 0 Then
'      'диаметр по-умолчанию
'      intDiamVerhArm = FormSpecRost.TextBoxDiamVerhArmDef
'   Else
'      'после "в" может быть "н", или цифра
'      If Mid(strNameVal, intValue + 1, 1) Like "[1-9]" Then
'         'если цифра
'         intDiamVerhArm = ReturnDiamStandard(Val(Right(strNameVal, Len(strNameVal) - intValue)))
'      Else
'         'если не цифра
'         intDiamVerhArm = ReturnDiamStandard(Val(Right(strNameVal, Len(strNameVal) - (intValue + 1))))
'      End If
'      If intDiamVerhArm = 0 Then
'         strError = "Диаметр верхней арматуры не определен. "
'         Exit Property
'      End If
'   End If
'   intValue = InStr(strNameVal, "н")
'   If intValue = 0 Then
'      intDiamNizArm = FormSpecRost.TextBoxDiamNizArmDef
'   Else
'      'после "н" может быть только цифра
'      If Mid(strNameVal, intValue + 1, 1) Like "[1-9]" Then
'         intDiamNizArm = ReturnDiamStandard(Val(Right(strNameVal, Len(strNameVal) - intValue)))
'      End If
'      If intDiamNizArm = 0 Then
'         strError = "Диаметр нижней арматуры не определен. "
'         Exit Property
'      End If
'   End If
'
'   intValue = InStr(strNameVal, "п")
'   If intValue = 0 Then
'      intDiamPopArm = FormSpecRost.TextBoxDiamPopArmDef
'   Else
'      'после "н" может быть только цифра
'      If Mid(strNameVal, intValue + 1, 1) Like "[1-9]" Then
'         intDiamPopArm = ReturnDiamStandard(Val(Right(strNameVal, Len(strNameVal) - intValue)))
'      End If
'      If intDiamPopArm = 0 Then
'         strError = "Диаметр поперечной арматуры не определен. "
'         Exit Property
'      End If
'   End If
'
'   'проверяем если есть скобки (6) - высота ростверка
'   intValue = InStr(strFirstName, "(")
'   If intValue <> 0 Then
'      'определяем кол-во
'      intValue = Val(Mid(strFirstName, intValue + 1))
'      If intValue <> 0 Then
'        intHeightRost = intValue * 100
'        bolHeightRostInName = True
'      Else
'        strPrim = "Непонятно что в скобках!"
'      End If
'   End If
'
'End Property

Private Function ReturnLenHvosta(Nomer As Integer) As Integer
   
   Select Case Nomer
      Case 0
         ReturnLenHvosta = FormSpecRost.TextBoxHvost0
      Case 1
         ReturnLenHvosta = FormSpecRost.TextBoxHvost1
      Case 2
         ReturnLenHvosta = FormSpecRost.TextBoxHvost2
      Case 3
         ReturnLenHvosta = FormSpecRost.TextBoxHvost3
      Case 4
         ReturnLenHvosta = FormSpecRost.TextBoxHvost4
      Case 5
         ReturnLenHvosta = FormSpecRost.TextBoxHvost5
      Case 6
         ReturnLenHvosta = FormSpecRost.TextBoxHvost6
      Case 7
         ReturnLenHvosta = FormSpecRost.TextBoxHvost7
      Case 8
         ReturnLenHvosta = FormSpecRost.TextBoxHvost8
      Case 9
         ReturnLenHvosta = FormSpecRost.TextBoxHvost9
   End Select
   
End Function

Private Function ReturnDiamStandard(Diam As Integer) As Integer
   'проверка соответствия входного диаметра списку стандартных диаметров арматуры
      
   Select Case Diam
      Case 6
         ReturnDiamStandard = Diam
      Case 8
         ReturnDiamStandard = Diam
      Case 10
         ReturnDiamStandard = Diam
      Case 12
         ReturnDiamStandard = Diam
      Case 14
         ReturnDiamStandard = Diam
      Case 16
         ReturnDiamStandard = Diam
      Case 18
         ReturnDiamStandard = Diam
      Case 20
         ReturnDiamStandard = Diam
      Case 22
         ReturnDiamStandard = Diam
      Case 25
         ReturnDiamStandard = Diam
      Case 28
         ReturnDiamStandard = Diam
      Case 32
         ReturnDiamStandard = Diam
      Case 36
         ReturnDiamStandard = Diam
      Case 40
         ReturnDiamStandard = Diam
      Case Else
         ReturnDiamStandard = 0
   End Select
   
End Function

Public Sub ObrabParam()
  'обработка введенных параметров каркаса
  'расчет массы
  Dim intVal As Integer
  
  On Error Resume Next
  
  If strError <> "" Then Exit Sub
  
  'определяем рабочую длину каркаса
  intLenRabPlusDopShag = intLenRab + intShagDopPopSter
  If bolD = True Then
    '!!!изменение. При повторном расчете длина увеличивается! Ошибка.
    'intLenRab = intLenRab + intShagDopPopSter
    'intLenRabPlusDopShag = intLenRab + intShagDopPopSter ' вынес перед условием if
    'кол-во поперечных стержней
    intKolPopSterPlosKar = intN + 2
  Else
    'кол-во поперечных стержней
    intKolPopSterPlosKar = intN + 1
  End If
  
  'длина продольной арматуры
  intLenProdolArm = intLenRabPlusDopShag + intHvostLeft + intHvostRight
  
  'единичная масса верхнего стержня кг
  dMassaEdVerhSter = Functions.GetMassaDiamPM(intDiamVerhArm) * (intLenProdolArm / 1000)
  'единичная масса нижнего стержня кг
  dMassaEdNizSter = Functions.GetMassaDiamPM(intDiamNizArm) * (intLenProdolArm / 1000)
  'длина поперечного стержня (расст между продол арм + по 25 выпуски)
  intLenPopArm = intHeightRost - intCenterNizArm - intCenterVerhArm + 50
  'единичная масса поперечного стержня кг
  dMassaEdPopSter = Functions.GetMassaDiamPM(intDiamPopArm) * intLenPopArm / 1000
  'масса плоского каркаса
  dMassaPlosKar = dMassaEdVerhSter + dMassaEdNizSter + dMassaEdPopSter * intKolPopSterPlosKar
    
  'для простр.кркасов расчитываем связевую арматуру
  If bolP = True Then
    'длина связевой арм
    If FormSpecRost.CheckBoxMarkaK.Value = False Then
      intLenSvyzArm = intLenSech - pclOptions.piLenSvyzB
    Else
      intLenSvyzArm = intLenSech - pclOptions.piLenSvyzBK
    End If
    'ед.масса связевого стержня
    dMassaEdSvyzNizSter = Functions.GetMassaDiamPM(intDiamSvyzNizArm) * intLenSvyzArm / 1000
    dMassaEdSvyzVerhSter = Functions.GetMassaDiamPM(intDiamSvyzVerhArm) * intLenSvyzArm / 1000
    'кол-во связевых верхних стержней
    intKolSvyzVerhSter = intLenRabPlusDopShag \ intShagSvyzVerhArm + 1 'деление нацело
    intVal = intLenRabPlusDopShag Mod intShagSvyzVerhArm
    If intVal > 25 Then intKolSvyzVerhSter = intKolSvyzVerhSter + 1
    'кол-во связевых нижних стержней
    intKolSvyzNizSter = intLenRabPlusDopShag \ intShagSvyzNizArm + 1 'деление нацело
    intVal = intLenRab Mod intShagSvyzNizArm
    If intVal > 25 Then intKolSvyzNizSter = intKolSvyzNizSter + 1
    'масса простран.каркаса
    dMassaProsKar = intP * dMassaPlosKar + dMassaEdSvyzNizSter * intKolSvyzNizSter + dMassaEdSvyzVerhSter * intKolSvyzVerhSter
  End If
  
  'наименовыания для стержней
  sNaimVerhArm = intDiamVerhArm & "-" & sKlassVerhArm & " " & sGOSTVerhArm & " L=" & intLenProdolArm
  sNaimNizArm = intDiamNizArm & "-" & sKlassNizArm & " " & sGOSTNizArm & " L=" & intLenProdolArm
  sNaimPopArm = intDiamPopArm & "-" & sKlassPopArm & " " & sGOSTPopArm & " L=" & intLenPopArm
  sNaimSvyzVerhArm = intDiamSvyzVerhArm & "-" & sKlassSvyzVerhArm & " " & sGOSTSvyzVerhArm & " L=" & intLenSvyzArm
  sNaimSvyzNizArm = intDiamSvyzNizArm & "-" & sKlassSvyzNizArm & " " & sGOSTSvyzNizArm & " L=" & intLenSvyzArm
  
  If Err Then
    strError = Err.Description
    Err.Clear
  End If
  
End Sub

Public Function ObrabName(sFirstNameProsKar As String)
  'способ посимвольной обработки имени простр каркаса
  'пример марки каркаса 4П41КД-вн22п10(6)
  
  Dim i As Integer
'  Dim strFirstName As String
  Dim sValue As String
  Dim Value As Variant
  Dim aValue As Variant
  Dim sDoTire As String
  Dim sPosleTire As String
  Dim iValue As Integer
  Dim iHvostik As Integer
  
'  iValue = InStr(sFirstNameProsKar, "(")
'  If iValue = 0 Then
'    strFirstName = sFirstNameProsKar
'  Else
'    strFirstName = Left(sFirstNameProsKar, iValue - 1)
'  End If
  strFirstName = sFirstNameProsKar
  
  strError = ""
  
  'начальное значение кол-ва каркасов(блоков на чертеже)
   intKolKar = 1
    
  'все что после "-"
  iValue = InStr(strFirstName, "-")
  If iValue <> 0 Then
    sPosleTire = Mid(strFirstName, iValue + 1)
    sDoTire = Left(strFirstName, iValue - 1)
  Else
    'нет "-"
    sDoTire = strFirstName
  End If
  
  'до тире "-"
  iValue = InStr(sDoTire, "П")
  If iValue <> 0 Then
    bolP = True
    'разделяем строку по П
    aValue = Split(sDoTire, "П")
    If UBound(aValue) <> 1 Then
      strError = "Ошибка при разделении строки имени каркаса по П."
      Exit Function
    End If
    iValue = Val(aValue(0))
    If aValue(0) <> iValue Or iValue = 0 Or iValue > 99 Then
      strError = "Кол-во плоских каркасов не определено."
      Exit Function
    End If
    'кол-во плоских каркасов
    intP = iValue
    'имя плоского каркаса
    If sPosleTire = "" Then
      strPlosKarName = aValue(1)
    Else
      strPlosKarName = aValue(1) & "-" & sPosleTire
    End If
  Else
    'плоский каркас
    strPlosKarName = strFirstName
  End If
  
  'разделяем по К имя плоского каркаса до тире
  iValue = InStr(strPlosKarName, "-")
  If iValue <> 0 Then
    'имя плоского каркаса до тире
    sValue = Left(strPlosKarName, iValue - 1)
  Else
    sValue = strPlosKarName
  End If
  aValue = Split(sValue, "К")
  If UBound(aValue) <> 1 Then
    strError = "Ошибка при разделении строки имени каркаса по К."
    Exit Function
  End If
  iValue = Val(aValue(0))
  If aValue(0) <> iValue Or iValue < 2 Or iValue > 99 Then
    strError = "Кол-во n*150 не определено."
    Exit Function
  End If
  
  If FormSpecRost.CheckBoxMarkaK.Value = False Then
    iHvostik = 20
  Else
    iHvostik = 30
  End If
  
  'кол-во n (n*150)
  intN = iValue
  intLenRab = intN * 150
  If aValue(1) = "" Then
    'значит тип каркаса К
    strType = "К"
    intHvostRight = iHvostik
    intHvostLeft = iHvostik
  Else
    'первый символ после К
    sValue = Left(aValue(1), 1)
    If sValue = "Д" Then
      strType = "КД"
      'определяем хвосты
      Value = Val(Mid(aValue(1), 2))
      iValue = Value
      If iValue <> Value Or iValue > 99 Then
        strError = "Хвосты не определены."
        Exit Function
      End If
      If iValue < 10 Then
        intHvostRight = pclOptions.GetLenHvosta(iValue)
        intHvostLeft = pclOptions.GetLenHvosta(0)
      Else
        sValue = Right(aValue(1), 2)
        iValue = Left(sValue, 1)
        intHvostRight = pclOptions.GetLenHvosta(iValue)
        iValue = Right(sValue, 1)
        intHvostLeft = pclOptions.GetLenHvosta(iValue)
      End If
    ElseIf sValue = "О" Then
      strType = "КО"
      'определяем хвост
      Value = Val(Mid(aValue(1), 2))
      iValue = Value
      If iValue <> Value Or iValue > 9 Then
        strError = "Хвосты не определены."
        Exit Function
      End If
      intHvostRight = pclOptions.GetLenHvosta(iValue)
      intHvostLeft = iHvostik
    Else
      strError = "Тип каркаса не определен."
      Exit Function
    End If
  End If
  
  'обрабатываем строку после "-"
  If sPosleTire = "" Then
    'стандартные диаметры
    intDiamVerhArm = pclOptions.piDiamKarVerhDef
    intDiamNizArm = pclOptions.piDiamKarNizDef
    intDiamPopArm = pclOptions.piDiamKarPopDef
  Else
    iValue = InStr(sPosleTire, "в")
    If iValue <> 0 Then
      'определяем диаметры верхней
      sValue = Mid(sPosleTire, iValue + 1, 1)
      If sValue = "н" Then
        Value = Val(Mid(sPosleTire, iValue + 2))
      Else
        Value = Val(Mid(sPosleTire, iValue + 1))
      End If
      iValue = Value
      If iValue <> Value Or ProvDiamStandard(iValue) = False Then
        strError = "Не определен диаметр верхней арматуры."
        Exit Function
      End If
      intDiamVerhArm = iValue
    Else
      'стандартный верхний диаметр
      intDiamVerhArm = pclOptions.piDiamKarVerhDef
    End If
    iValue = InStr(sPosleTire, "н")
    If iValue <> 0 Then
      Value = Val(Mid(sPosleTire, iValue + 1))
      iValue = Value
      If iValue <> Value Or ProvDiamStandard(iValue) = False Then
        strError = "Не определен диаметр нижней арматуры."
        Exit Function
      End If
      intDiamNizArm = iValue
    Else
      'стандартный нижний диаметр
      intDiamNizArm = pclOptions.piDiamKarNizDef
    End If
    iValue = InStr(sPosleTire, "п")
    If iValue <> 0 Then
      Value = Val(Mid(sPosleTire, iValue + 1))
      iValue = Value
      If iValue <> Value Or ProvDiamStandard(iValue) = False Then
        strError = "Не определен диаметр поперечной арматуры."
        Exit Function
      End If
      intDiamPopArm = iValue
    Else
      'стандартный поперечный диаметр
      intDiamPopArm = pclOptions.piDiamKarPopDef
    End If
    iValue = InStr(sPosleTire, "д")
    If iValue <> 0 Then
      'есть доп.поп.стер.
      'intLenRab = intLenRab + 100
      bolD = True
      If FormSpecRost.CheckBoxMarkaK.Value = True Then
        Value = Val(Mid(sPosleTire, iValue + 1))
        iValue = Value
        If iValue <> Value Then
          strError = "Не определен шаг доп.поп.стержня"
          Exit Function
        End If
        If iValue <> 0 Then
          intShagDopPopSter = iValue * 10
        Else
          intShagDopPopSter = pclOptions.piShagDopPopSterDef
        End If
      Else
        intShagDopPopSter = pclOptions.piShagDopPopSterDef
      End If
    End If
  End If 'sPosleTire <> "" Then
  
  'проверяем если есть скобки (6) - высота ростверка
  Dim dValue As Double
   iValue = InStr(sFirstNameProsKar, "(")
   If iValue <> 0 Then
      'определяем кол-во
      dValue = Val(Mid(sFirstNameProsKar, iValue + 1))
      If dValue <> 0 Then
        intHeightRost = dValue * 100
        bolHeightRostInName = True
'        strPlosKarName = strPlosKarName & "(" & dValue & ")"
'      Else
'        strPrim = "Неопределено что в скобках (высота ростверка)!"
      End If
   End If
   
  'марка плос кар типа К1
  If strMarkaK <> "" Then
    iValue = InStr(strMarkaK, "(")
    If iValue <> 0 Then
      sValue = Left(strMarkaK, iValue - 1)
    Else
      sValue = strMarkaK
    End If
    If bolP = True Then
      iValue = InStr(sValue, "П")
      If iValue <> 0 Then
        If Val(sValue) <> intP Then
          strError = "МаркаК не соответствует марке пространственного каркаса."
          Exit Function
        End If
        strMarkaKPlos = Mid(sValue, iValue + 1)
      End If
    Else
      strMarkaKPlos = strMarkaK
    End If
  End If
  
End Function

Attribute VB_Name = "clListSoderg"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public piStr As Integer
Public psShifrLista As String
Public psNaimenLista As String

Attribute VB_Name = "clOptions"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
  
'хранение настроек
'сохранение настроек в ини
'згрузка настроек из ини
  
  Dim oIni As ClassINI
  
  'исходные данные
  Public pForShtampShifr As String 'шифр
  Public pForShtampBS As Boolean
  Public pForShtampNPart As String
  Public pForShtampAdres As String
  Public pForShtampNaimenObject As String
  Public pForShtampPost1 As String
  Public pForShtampPost2 As String
  Public pForShtampPost3 As String
  Public pForShtampPost4 As String
  Public pForShtampPost5 As String
  Public pForShtampPost6 As String
  Public pForShtampFam1 As String
  Public pForShtampFam2 As String
  Public pForShtampFam3 As String
  Public pForShtampFam4 As String
  Public pForShtampFam5 As String
  Public pForShtampFam6 As String
  Public pForSgtampChkBox1ForTitulPost As Boolean
  Public pForSgtampChkBox2ForTitulPost As Boolean
  Public pForSgtampChkBox3ForTitulPost As Boolean
  Public pForSgtampChkBox1ForShtamp As Boolean
  Public pForSgtampChkBox2ForShtamp As Boolean
  Public pForSgtampChkBox3ForShtamp As Boolean
  Public pForSgtampChkBox4ForShtamp As Boolean
  Public pForSgtampChkBox5ForShtamp As Boolean
  Public pForSgtampChkBox6ForShtamp As Boolean
  
  'постоянные имена для типов блоков
  Public psSetkaConst As String
  Public psDopSterConst  As String
  'определение атрибутов и их значений для блока каркаса
  Public psKarAtrMarkaLayer As String
  Public psKarAtrConstrLayer As String
  Public psKarAtrConstrText As String
  'имена слоев
  Public psKarLayer As String
  Public psSetkyLayer As String
  Public psDopSterLayer As String
  'радиус наложения
  Public pintRadNalog As Integer
  Public piShagDopPopSterDef As Integer
  'диаметры каркаса по умолчанию
  Public piDiamKarVerhDef As Integer
  Public piDiamKarNizDef As Integer
  Public piDiamKarPopDef As Integer
  'классы арматуры
  Public psKlassVerhDef As String
  Public psKlassNizDef As String
  Public psKlassPopDef As String
  Public psKlassSvyzVerhDef As String
  Public psKlassSvyzNizDef As String
  Public psKlassSetokDef As String
  Public psKlassDopStergDef As String
  Public psKlassShpilekDef As String
  Public psGOSTVerhDef As String
  Public psGOSTNizDef As String
  Public psGOSTPopDef As String
  Public psGOSTSvyzVerhDef As String
  Public psGOSTSvyzNizDef As String
  Public psGOSTSetokDef As String
  Public psGOSTDopStergDef As String
  Public psGOSTShpilekDef As String
  'длины хвостов
  Dim aiLenHvost(9) As Integer
  'длины хвостов для Кирпички
  Dim aiLenHvostK(9) As Integer
  'значения поумолчанию для простран каркасов (можно сделать трехмерный массив)
  Public iHeightRostDef As Integer 'высота ростверка (из aiHeightRostDef(0))
  Public iZachBetNizDef As Integer '= aiZachBetNizDef(0))
  Public iZachBetVerhDef As Integer '= aiZachBetVerhDef(0))
  Dim asNSechDef() As String
  Dim aiLenSechDef() As Integer
  Dim aiHeightRostDef() As Integer
  Dim aiShagSvyzNizArmDef() As Integer
  Dim aiShagSvyzVerhArmDef() As Integer
  Dim aiDiamSvyzNizArmDef() As Integer
  Dim aiDiamSvyzVerhArmDef() As Integer
  Dim aiZachBetNizDef() As Integer
  Dim aiZachBetVerhDef() As Integer
  Dim abolUsilenie() As Boolean
  Dim aiUsLenSechDef() As Integer
  Dim aiUsDiamNizArmDef() As Integer
  Dim aiUsDiamVerhArmDef() As Integer
  Dim aiUsShagNizArmDef() As Integer
  Dim aiUsShagVerhArmDef() As Integer
  Dim asUsKlassNizArmDef() As String
  Dim asUsKlassVerhArmDef() As String
  Dim asUsGOSTNizArmDef() As String
  Dim asUsGOSTVerhArmDef() As String
  Dim asKlassVerhArmDef() As String
  Dim asKlassNizArmDef() As String
  Dim asKlassPopArmDef() As String
  Dim asKlassSvyzNizArmDef() As String
  Dim asKlassSvyzVerhArmDef() As String
  Dim asGOSTNizArmDef() As String
  Dim asGOSTVerhArmDef() As String
  Dim asGOSTPopArmDef() As String
  Dim asGOSTSvyzNizArmDef() As String
  Dim asGOSTSvyzVerhArmDef() As String
  'значения поумолчанию для сечений плоских каркасов
  Dim asNSechPlosDef() As String
  Dim aiLenSechPlosDef() As Integer
  Dim aiKolInSechPlosDef() As Integer 'кол-во плоских каркасов в сечении
  Dim aiDiamVerhSvyzPlosDef() As Integer
  Dim aiDiamNizSvyzPlosDef() As Integer
  Dim aiShagVerhSvyzPlosDef() As Integer
  Dim aiShagNizSvyzPlosDef() As Integer
  Dim asKlassVerhSvyzPlosDef() As String
  Dim asKlassNizSvyzPlosDef() As String
  Dim asGOSTVerhSvyzPlosDef() As String
  Dim asGOSTNizSvyzPlosDef() As String
  'параметры стержней для перепадов
  Public piDiamSter1Perepada As Integer 'стержень по высоте перепада
  Public piDiamSter2Perepada As Integer 'по ширине перепада
  Public piDiamSter3Perepada As Integer 'по ширине ростверка перепада
  Public piDiamSter4Perepada As Integer 'шпилька
  Public psKlassSter1Perepada As String
  Public psKlassSter2Perepada As String
  Public psKlassSter3Perepada As String
  Public psKlassSter4Perepada As String
  Public psGostSter1Perepada As String
  Public psGostSter2Perepada As String
  Public psGostSter3Perepada As String
  Public psGostSter4Perepada As String
  'Для расчета длины связевых стержней пространственных каркасов
  Public piLenSvyzB As Integer
  Public piLenSvyzBK As Integer
  'МаркаК
  Public psMarkaKTag As String 'значение TagString для атрибута МаркиК
  Public pbMarkaKValue As Boolean 'галка расчета по кирпичке (МаркеК)
  'Последний номер расчета (кол-во сохраненных расчеетов в ини)
  
  'Секция в ини для сохранения расчетов
  Const scSectionForSavedRaschet As String = "Сохраненные расчеты"
  
  
Public Sub SaveOptionsToIni()
  'сохранение настроек(переменных) в ини файл
  'имя для ини файла = pcsVBProjectName.ini
  'в корне с макросом
  
  Dim sValue As String
  
  'УДАЛЯТЬ ИНИ ФАЙЛ!!! перед записью
  'Думаю да
  Dim sIniFile As String 'путь к ини файлу
  sIniFile = oIni.INIFile
  If sIniFile = "" Then
    'MsgBox "Файл настроек не определен. Выход.", , pcsVBProjectName
    Exit Sub
  End If
  Kill sIniFile
  Dim sFileName As String
  sFileName = pcsVBProjectName & ".ini"
  oIni.CreateIni sFileName, psMacroFolder & "\Ini"
  
  'загрузка параметров для вкладки "Настройки"
  'Секция=Настройки
  'далее все по ключам
  
  On Error GoTo HasError
  
  'Слои
  oIni.WriteFile "Настройки", "Слой для каркасов", psKarLayer
  
  'слой для сеток
  oIni.WriteFile "Настройки", "Слой для сеток", psSetkyLayer
  'слой для доп.стержней
  oIni.WriteFile "Настройки", "Слой для доп.стержней", psDopSterLayer
  'определение атрибутов каркаса
  'атр марки на слое
  oIni.WriteFile "Настройки", "Атр марки каркаса на слое", psKarAtrMarkaLayer
  'атр конструкции на слое
  oIni.WriteFile "Настройки", "Атр конструкции каркаса на слое", psKarAtrConstrLayer
  'значение атр конструкции
  oIni.WriteFile "Настройки", "Значение атр конструкции каркаса", psKarAtrConstrText
  'постоянная часть имени для блока сетки
  oIni.WriteFile "Настройки", "Постоянное имя для блока сетки", psSetkaConst
  'постоянная часть имени для блока доп.стержня
  oIni.WriteFile "Настройки", "Постоянное имя для блока доп.стержня", psDopSterConst
  'радиус наложения
  oIni.WriteFile "Настройки", "Радиус наложения", CStr(pintRadNalog)
  'шаг доп.поп.стержня
  oIni.WriteFile "Настройки", "Шаг доп.поп.стержня", CStr(piShagDopPopSterDef)
  'хвосты
  sValue = GetStringHvosty(False)
  oIni.WriteFile "Настройки", "Длины хвостов", sValue
  'хвосты для Кирпички
  sValue = GetStringHvosty(True)
  oIni.WriteFile "Настройки", "Длины хвостов К", sValue
  'диаметры поумолчанию для каркасов
  oIni.WriteFile "Настройки", "Диаметр верхней арм каркаса", CStr(piDiamKarVerhDef)
  oIni.WriteFile "Настройки", "Диаметр нижней арм каркаса", CStr(piDiamKarNizDef)
  oIni.WriteFile "Настройки", "Диаметр поперечной арм каркаса", CStr(piDiamKarPopDef)
  'классы арматуры
  oIni.WriteFile "Настройки", "Класс верхней арматуры", psKlassVerhDef
  oIni.WriteFile "Настройки", "Класс нижней арматуры", psKlassNizDef
  oIni.WriteFile "Настройки", "Класс поперечной арматуры", psKlassPopDef
  oIni.WriteFile "Настройки", "Класс связевой верхней арматуры", psKlassSvyzVerhDef
  oIni.WriteFile "Настройки", "Класс связевой нижней арматуры", psKlassSvyzNizDef
  oIni.WriteFile "Настройки", "Класс арматуры сеток", psKlassSetokDef
  oIni.WriteFile "Настройки", "Класс доп.стержней", psKlassDopStergDef
  oIni.WriteFile "Настройки", "Класс шпилек", psKlassShpilekDef
  oIni.WriteFile "Настройки", "Норма верхней арматуры", psGOSTVerhDef
  oIni.WriteFile "Настройки", "Норма нижней арматуры", psGOSTNizDef
  oIni.WriteFile "Настройки", "Норма поперечной арматуры", psGOSTPopDef
  oIni.WriteFile "Настройки", "Норма связевой верхней арматуры", psGOSTSvyzVerhDef
  oIni.WriteFile "Настройки", "Норма связевой нижней арматуры", psGOSTSvyzNizDef
  oIni.WriteFile "Настройки", "Норма арматуры сеток", psGOSTSetokDef
  oIni.WriteFile "Настройки", "Норма доп.стержней", psGOSTDopStergDef
  oIni.WriteFile "Настройки", "Норма шпилек", psGOSTShpilekDef
  'TagString МаркиК
  oIni.WriteFile "Настройки", "Tag атрибута маркиК", psMarkaKTag
  'галочка расчета по МаркеК
  If pbMarkaKValue = False Then
    sValue = "false"
  Else
   sValue = "true"
  End If
  oIni.WriteFile "Настройки", "Расчет по МаркеК", sValue
  
  'Для расчета связевых стержней, Шир сеч - b
  oIni.WriteFile "Настройки", "Суммарный защитный слой связевых стержней", CStr(piLenSvyzB)
  oIni.WriteFile "Настройки", "Суммарный защитный слой связевых стержней К", CStr(piLenSvyzBK)
  
  'считываем параметры простр.каркасов для номеров сеченирй
  'секция = Параметры простр каркасов
  'ключ = имени переменной
  'значение вида =ЗначениеДляNSech;ЗначениеДляNSech;...
  'номера сечений
  sValue = GetStringNSechDef
  oIni.WriteFile "Параметры сечений простр каркасов", "Номер сечения", sValue
  sValue = GetStringArrayIntDef("Ширина сечения", True)
  oIni.WriteFile "Параметры сечений простр каркасов", "Ширина сечения", sValue
  sValue = GetStringArrayIntDef("Высота ростверка", True)
  oIni.WriteFile "Параметры сечений простр каркасов", "Высота ростверка", sValue
  sValue = GetStringArrayIntDef("Шаг верхней связевой", True)
  oIni.WriteFile "Параметры сечений простр каркасов", "Шаг верхней связевой", sValue
  sValue = GetStringArrayIntDef("Шаг нижней связевой", True)
  oIni.WriteFile "Параметры сечений простр каркасов", "Шаг нижней связевой", sValue
  sValue = GetStringArrayIntDef("Диаметр верхней связевой", True)
  oIni.WriteFile "Параметры сечений простр каркасов", "Диаметр верхней связевой", sValue
  sValue = GetStringArrayIntDef("Диаметр нижней связевой", True)
  oIni.WriteFile "Параметры сечений простр каркасов", "Диаметр нижней связевой", sValue
  sValue = GetStringArrayIntDef("Защ.слой нижний", True)
  oIni.WriteFile "Параметры сечений простр каркасов", "Защ.слой нижний", sValue
  sValue = GetStringArrayIntDef("Защ.слой верхний", True)
  oIni.WriteFile "Параметры сечений простр каркасов", "Защ.слой верхний", sValue
  sValue = GetStringArrayBolUs()
  oIni.WriteFile "Параметры сечений простр каркасов", "Признак усиления", sValue
  sValue = GetStringArrayIntDef("Ширина усиления", True)
  oIni.WriteFile "Параметры сечений простр каркасов", "Ширина усиления", sValue
  sValue = GetStringArrayIntDef("Шаг верхней усиливающей", True)
  oIni.WriteFile "Параметры сечений простр каркасов", "Шаг верхней усиливающей", sValue
  sValue = GetStringArrayIntDef("Шаг нижней усиливающей", True)
  oIni.WriteFile "Параметры сечений простр каркасов", "Шаг нижней усиливающей", sValue
  sValue = GetStringArrayIntDef("Диаметр верхней усиливающей", True)
  oIni.WriteFile "Параметры сечений простр каркасов", "Диаметр верхней усиливающей", sValue
  sValue = GetStringArrayIntDef("Диаметр нижней усиливающей", True)
  oIni.WriteFile "Параметры сечений простр каркасов", "Диаметр нижней усиливающей", sValue
  sValue = GetStringArrayStrDef("Класс верхней усиливающей", True)
  oIni.WriteFile "Параметры сечений простр каркасов", "Класс верхней усиливающей", sValue
  sValue = GetStringArrayStrDef("Класс нижней усиливающей", True)
  oIni.WriteFile "Параметры сечений простр каркасов", "Класс нижней усиливающей", sValue
  sValue = GetStringArrayStrDef("Норма верхней усиливающей", True)
  oIni.WriteFile "Параметры сечений простр каркасов", "Норма верхней усиливающей", sValue
  sValue = GetStringArrayStrDef("Норма нижней усиливающей", True)
  oIni.WriteFile "Параметры сечений простр каркасов", "Норма нижней усиливающей", sValue
  sValue = GetStringArrayStrDef("Класс верхней", True)
  oIni.WriteFile "Параметры сечений простр каркасов", "Класс верхней", sValue
  sValue = GetStringArrayStrDef("Класс нижней", True)
  oIni.WriteFile "Параметры сечений простр каркасов", "Класс нижней", sValue
  sValue = GetStringArrayStrDef("Класс поперечной", True)
  oIni.WriteFile "Параметры сечений простр каркасов", "Класс поперечной", sValue
  sValue = GetStringArrayStrDef("Класс верхней связевой", True)
  oIni.WriteFile "Параметры сечений простр каркасов", "Класс верхней связевой", sValue
  sValue = GetStringArrayStrDef("Класс нижней связевой", True)
  oIni.WriteFile "Параметры сечений простр каркасов", "Класс нижней связевой", sValue
  sValue = GetStringArrayStrDef("Норма верхней", True)
  oIni.WriteFile "Параметры сечений простр каркасов", "Норма верхней", sValue
  sValue = GetStringArrayStrDef("Норма нижней", True)
  oIni.WriteFile "Параметры сечений простр каркасов", "Норма нижней", sValue
  sValue = GetStringArrayStrDef("Норма поперечной", True)
  oIni.WriteFile "Параметры сечений простр каркасов", "Норма поперечной", sValue
  sValue = GetStringArrayStrDef("Норма верхней связевой", True)
  oIni.WriteFile "Параметры сечений простр каркасов", "Норма верхней связевой", sValue
  sValue = GetStringArrayStrDef("Норма нижней связевой", True)
  oIni.WriteFile "Параметры сечений простр каркасов", "Норма нижней связевой", sValue
  
  'сохраняем параметры сечений плоских каркасов
  sValue = GetStringNSechPlosDef
  oIni.WriteFile "Параметры сечений плоских каркасов", "Номер сечения", sValue
  sValue = GetStringArrayIntDef("Ширина сечения", False)
  oIni.WriteFile "Параметры сечений плоских каркасов", "Ширина сечения", sValue
  sValue = GetStringArrayIntDef("Кол-во каркасов в сечении", False)
  oIni.WriteFile "Параметры сечений плоских каркасов", "Кол-во каркасов в сечении", sValue
  sValue = GetStringArrayIntDef("Диаметр верхней связевой арматуры", False)
  oIni.WriteFile "Параметры сечений плоских каркасов", "Диаметр верхней связевой арматуры", sValue
  sValue = GetStringArrayIntDef("Диаметр нижней связевой арматуры", False)
  oIni.WriteFile "Параметры сечений плоских каркасов", "Диаметр нижней связевой арматуры", sValue
  sValue = GetStringArrayIntDef("Шаг верхней связевой арматуры", False)
  oIni.WriteFile "Параметры сечений плоских каркасов", "Шаг верхней связевой арматуры", sValue
  sValue = GetStringArrayIntDef("Шаг нижней связевой арматуры", False)
  oIni.WriteFile "Параметры сечений плоских каркасов", "Шаг нижней связевой арматуры", sValue
  sValue = GetStringArrayStrDef("Класс верхней связевой арматуры", False)
  oIni.WriteFile "Параметры сечений плоских каркасов", "Класс верхней связевой арматуры", sValue
  sValue = GetStringArrayStrDef("Класс нижней связевой арматуры", False)
  oIni.WriteFile "Параметры сечений плоских каркасов", "Класс нижней связевой арматуры", sValue
  sValue = GetStringArrayStrDef("ГОСТ верхней связевой арматуры", False)
  oIni.WriteFile "Параметры сечений плоских каркасов", "ГОСТ верхней связевой арматуры", sValue
  sValue = GetStringArrayStrDef("ГОСТ нижней связевой арматуры", False)
  oIni.WriteFile "Параметры сечений плоских каркасов", "ГОСТ нижней связевой арматуры", sValue
  
  'параметры перепадов
  'параметры стержней для перепадов
  oIni.WriteFile "Перепады", "piDiamSter1Perepada", CStr(piDiamSter1Perepada)
  oIni.WriteFile "Перепады", "piDiamSter2Perepada", CStr(piDiamSter2Perepada)
  oIni.WriteFile "Перепады", "piDiamSter3Perepada", CStr(piDiamSter3Perepada)
  oIni.WriteFile "Перепады", "piDiamSter4Perepada", CStr(piDiamSter4Perepada)
  oIni.WriteFile "Перепады", "psKlassSter1Perepada", psKlassSter1Perepada
  oIni.WriteFile "Перепады", "psKlassSter2Perepada", psKlassSter2Perepada
  oIni.WriteFile "Перепады", "psKlassSter3Perepada", psKlassSter3Perepada
  oIni.WriteFile "Перепады", "psKlassSter4Perepada", psKlassSter4Perepada
  oIni.WriteFile "Перепады", "psGostSter1Perepada", psGostSter1Perepada
  oIni.WriteFile "Перепады", "psGostSter2Perepada", psGostSter2Perepada
  oIni.WriteFile "Перепады", "psGostSter3Perepada", psGostSter3Perepada
  oIni.WriteFile "Перепады", "psGostSter4Perepada", psGostSter4Perepada
  
  'Исходные данные (заполнение штампа и обложек)
  oIni.WriteFile "ИсходныеДанные", "pForShtampShifr", pForShtampShifr
  oIni.WriteFile "ИсходныеДанные", "pForShtampBS", CStr(pForShtampBS)
  oIni.WriteFile "ИсходныеДанные", "pForShtampNPart", pForShtampNPart
  oIni.WriteFile "ИсходныеДанные", "pForShtampAdres", pForShtampAdres
  oIni.WriteFile "ИсходныеДанные", "pForShtampNaimenObject", pForShtampNaimenObject
  oIni.WriteFile "ИсходныеДанные", "pForShtampPost1", pForShtampPost1
  oIni.WriteFile "ИсходныеДанные", "pForShtampPost2", pForShtampPost2
  oIni.WriteFile "ИсходныеДанные", "pForShtampPost3", pForShtampPost3
  oIni.WriteFile "ИсходныеДанные", "pForShtampPost4", pForShtampPost4
  oIni.WriteFile "ИсходныеДанные", "pForShtampPost5", pForShtampPost5
  oIni.WriteFile "ИсходныеДанные", "pForShtampPost6", pForShtampPost6
  oIni.WriteFile "ИсходныеДанные", "pForShtampFam1", pForShtampFam1
  oIni.WriteFile "ИсходныеДанные", "pForShtampFam2", pForShtampFam2
  oIni.WriteFile "ИсходныеДанные", "pForShtampFam3", pForShtampFam3
  oIni.WriteFile "ИсходныеДанные", "pForShtampFam4", pForShtampFam4
  oIni.WriteFile "ИсходныеДанные", "pForShtampFam5", pForShtampFam5
  oIni.WriteFile "ИсходныеДанные", "pForShtampFam6", pForShtampFam6
  oIni.WriteFile "ИсходныеДанные", "pForSgtampChkBox1ForTitulPost", CStr(pForSgtampChkBox1ForTitulPost)
  oIni.WriteFile "ИсходныеДанные", "pForSgtampChkBox2ForTitulPost", CStr(pForSgtampChkBox2ForTitulPost)
  oIni.WriteFile "ИсходныеДанные", "pForSgtampChkBox3ForTitulPost", CStr(pForSgtampChkBox3ForTitulPost)
  oIni.WriteFile "ИсходныеДанные", "pForSgtampChkBox1ForShtamp", CStr(pForSgtampChkBox1ForShtamp)
  oIni.WriteFile "ИсходныеДанные", "pForSgtampChkBox2ForShtamp", CStr(pForSgtampChkBox2ForShtamp)
  oIni.WriteFile "ИсходныеДанные", "pForSgtampChkBox3ForShtamp", CStr(pForSgtampChkBox3ForShtamp)
  oIni.WriteFile "ИсходныеДанные", "pForSgtampChkBox4ForShtamp", CStr(pForSgtampChkBox4ForShtamp)
  oIni.WriteFile "ИсходныеДанные", "pForSgtampChkBox5ForShtamp", CStr(pForSgtampChkBox5ForShtamp)
  oIni.WriteFile "ИсходныеДанные", "pForSgtampChkBox6ForShtamp", CStr(pForSgtampChkBox6ForShtamp)
  
  'сохранение данных о расчетах из комбобокса расчетов
'  SaveRaschetyToIni

Exit Sub
HasError:
  MsgBox Err.Description, vbCritical, pcsVBProjectName
End Sub

Public Sub LoadOptionsFromIni()
  'загрузка настроек(переменных) из ини
  Dim sValue As String
  
  'загрузка настроек из ини файла SpecRost.ini
  Set oIni = New ClassINI
  
  Const sFileName As String = pcsVBProjectName & ".ini"
  
  'проверка существования ини файла
  If Dir(psMacroFolder & "\Ini\" & sFileName) = "" Then
    MsgBox "Файл настроек не найден", vbCritical, pcsVBProjectName
    Exit Sub
  End If
  
  oIni.CreateIni sFileName, psMacroFolder & "\Ini"
  
  'загрузка параметров для вкладки "Настройки"
  'Секция=Настройки
  'далее все по ключам
  'Слои
  psKarLayer = oIni.GetFile("Настройки", "Слой для каркасов")
  If psKarLayer = "" Then
    psKarLayer = "Каркасы"
  End If
  FormSpecRost.TextBoxLayerKarDef = psKarLayer
  'слой для сеток
  psSetkyLayer = oIni.GetFile("Настройки", "Слой для сеток")
  If psSetkyLayer = "" Then
    psSetkyLayer = "Каркасы"
  End If
  FormSpecRost.TextBoxLayerSetkyDef = psSetkyLayer
  'слой для доп.стержней
  psDopSterLayer = oIni.GetFile("Настройки", "Слой для доп.стержней")
  If psDopSterLayer = "" Then
    psDopSterLayer = "Каркасы"
  End If
  FormSpecRost.TextBoxLayerDopSterDef = psDopSterLayer
  'определение атрибутов каркаса
  'атр марки на слое
  psKarAtrMarkaLayer = oIni.GetFile("Настройки", "Атр марки каркаса на слое")
  If psKarAtrMarkaLayer = "" Then
    psKarAtrMarkaLayer = "Att~Marka"
  End If
  'атр конструкции на слое
  psKarAtrConstrLayer = oIni.GetFile("Настройки", "Атр конструкции каркаса на слое")
  If psKarAtrConstrLayer = "" Then
    psKarAtrConstrLayer = "Att~Constr"
  End If
  'значение атр конструкции
  psKarAtrConstrText = oIni.GetFile("Настройки", "Значение атр конструкции каркаса")
  If psKarAtrConstrText = "" Then
    psKarAtrConstrText = "Ростверк"
  End If
  'постоянная часть имени для блока сетки
  psSetkaConst = oIni.GetFile("Настройки", "Постоянное имя для блока сетки")
  If psSetkaConst = "" Then
    psSetkaConst = "Сетка"
  End If
  FormSpecRost.TextBoxSetkyBlName = psSetkaConst
  'постоянная часть имени для блока доп.стержня
  psDopSterConst = oIni.GetFile("Настройки", "Постоянное имя для блока доп.стержня")
  If psDopSterConst = "" Then
    psDopSterConst = "Стержень"
  End If
  FormSpecRost.TextBoxDopSterBlName = psDopSterConst
  'радиус наложения
  pintRadNalog = Val(oIni.GetFile("Настройки", "Радиус наложения"))
  If pintRadNalog = 0 Then
    pintRadNalog = 100
  End If
  FormSpecRost.TextBoxRadNalog = pintRadNalog
  'шаг доп.поп.стержня
  piShagDopPopSterDef = Val(oIni.GetFile("Настройки", "Шаг доп.поп.стержня"))
  If piShagDopPopSterDef = 0 Then
    piShagDopPopSterDef = 100
  End If
  FormSpecRost.TextBoxShagDopPopSterDef = piShagDopPopSterDef
  'хвосты
  sValue = oIni.GetFile("Настройки", "Длины хвостов")
  GetArrayHvosty sValue, False
  FormSpecRost.TextBoxHvost0 = aiLenHvost(0)
  FormSpecRost.TextBoxHvost1 = aiLenHvost(1)
  FormSpecRost.TextBoxHvost2 = aiLenHvost(2)
  FormSpecRost.TextBoxHvost3 = aiLenHvost(3)
  FormSpecRost.TextBoxHvost4 = aiLenHvost(4)
  FormSpecRost.TextBoxHvost5 = aiLenHvost(5)
  FormSpecRost.TextBoxHvost6 = aiLenHvost(6)
  FormSpecRost.TextBoxHvost7 = aiLenHvost(7)
  FormSpecRost.TextBoxHvost8 = aiLenHvost(8)
  FormSpecRost.TextBoxHvost9 = aiLenHvost(9)
  'хвосты для Кирп
  sValue = oIni.GetFile("Настройки", "Длины хвостов К")
  GetArrayHvosty sValue, True
  FormSpecRost.TextBoxHvost0K = aiLenHvostK(0)
  FormSpecRost.TextBoxHvost1K = aiLenHvostK(1)
  FormSpecRost.TextBoxHvost2K = aiLenHvostK(2)
  FormSpecRost.TextBoxHvost3K = aiLenHvostK(3)
  FormSpecRost.TextBoxHvost4K = aiLenHvostK(4)
  FormSpecRost.TextBoxHvost5K = aiLenHvostK(5)
  FormSpecRost.TextBoxHvost6K = aiLenHvostK(6)
  FormSpecRost.TextBoxHvost7K = aiLenHvostK(7)
  FormSpecRost.TextBoxHvost8K = aiLenHvostK(8)
  FormSpecRost.TextBoxHvost9K = aiLenHvostK(9)
  'диаметры каркасов по умолчанию
  piDiamKarVerhDef = Val(oIni.GetFile("Настройки", "Диаметр верхней арм каркаса"))
  If piDiamKarVerhDef = 0 Then
    piDiamKarVerhDef = 12
  End If
  FormSpecRost.TextBoxDiamVerhArmDef = piDiamKarVerhDef
  piDiamKarNizDef = Val(oIni.GetFile("Настройки", "Диаметр нижней арм каркаса"))
  If piDiamKarNizDef = 0 Then
    piDiamKarNizDef = 10
  End If
  FormSpecRost.TextBoxDiamNizArmDef = piDiamKarNizDef
  piDiamKarPopDef = Val(oIni.GetFile("Настройки", "Диаметр поперечной арм каркаса"))
  If piDiamKarPopDef = 0 Then
    piDiamKarPopDef = 8
  End If
  FormSpecRost.TextBoxDiamPopArmDef = piDiamKarPopDef
  'классы арматуры
  psKlassVerhDef = oIni.GetFile("Настройки", "Класс верхней арматуры")
  If psKlassVerhDef = "" Then
    psKlassVerhDef = "A-III"
  End If
  FormSpecRost.TextBoxKlassVerhDef = psKlassVerhDef
  psKlassNizDef = oIni.GetFile("Настройки", "Класс нижней арматуры")
  If psKlassNizDef = "" Then
    psKlassNizDef = "A-III"
  End If
  FormSpecRost.TextBoxKlassNizDef = psKlassNizDef
  psKlassPopDef = oIni.GetFile("Настройки", "Класс поперечной арматуры")
  If psKlassPopDef = "" Then
    psKlassPopDef = "A-III"
  End If
  FormSpecRost.TextBoxKlassPopDef = psKlassPopDef
  psKlassSvyzVerhDef = oIni.GetFile("Настройки", "Класс связевой верхней арматуры")
  If psKlassSvyzVerhDef = "" Then
    psKlassSvyzVerhDef = "A-III"
  End If
  FormSpecRost.TextBoxKlassSvyzVerhDef = psKlassSvyzVerhDef
  psKlassSvyzNizDef = oIni.GetFile("Настройки", "Класс связевой нижней арматуры")
  If psKlassSvyzNizDef = "" Then
    psKlassSvyzNizDef = "A-III"
  End If
  FormSpecRost.TextBoxKlassSvyzNizDef = psKlassSvyzNizDef
  psKlassSetokDef = oIni.GetFile("Настройки", "Класс арматуры сеток")
  If psKlassSetokDef = "" Then
    psKlassSetokDef = "A-III"
  End If
  FormSpecRost.TextBoxKlassSetokDef = psKlassSetokDef
  psKlassDopStergDef = oIni.GetFile("Настройки", "Класс доп.стержней")
  If psKlassDopStergDef = "" Then
    psKlassDopStergDef = "A-III"
  End If
  FormSpecRost.TextBoxKlassDopStergDef = psKlassDopStergDef
  psKlassShpilekDef = oIni.GetFile("Настройки", "Класс шпилек")
  If psKlassShpilekDef = "" Then
    psKlassShpilekDef = "A-I"
  End If
  FormSpecRost.TextBoxKlassShpilekDef = psKlassShpilekDef
  psGOSTVerhDef = oIni.GetFile("Настройки", "Норма верхней арматуры")
  If psGOSTVerhDef = "" Then
    psGOSTVerhDef = "ГОСТ 5781-82"
  End If
  FormSpecRost.TextBoxGOSTVerhDef = psGOSTVerhDef
  psGOSTNizDef = oIni.GetFile("Настройки", "Норма нижней арматуры")
  If psGOSTNizDef = "" Then
    psGOSTNizDef = "ГОСТ 5781-82"
  End If
  FormSpecRost.TextBoxGOSTNizDef = psGOSTNizDef
  psGOSTPopDef = oIni.GetFile("Настройки", "Норма поперечной арматуры")
  If psGOSTPopDef = "" Then
    psGOSTPopDef = "ГОСТ 5781-82"
  End If
  FormSpecRost.TextBoxGOSTPopDef = psGOSTPopDef
  psGOSTSvyzVerhDef = oIni.GetFile("Настройки", "Норма связевой верхней арматуры")
  If psGOSTSvyzVerhDef = "" Then
    psGOSTSvyzVerhDef = "ГОСТ 5781-82"
  End If
  FormSpecRost.TextBoxGOSTSvyzVerhDef = psGOSTSvyzVerhDef
  psGOSTSvyzNizDef = oIni.GetFile("Настройки", "Норма связевой нижней арматуры")
  If psGOSTSvyzNizDef = "" Then
    psGOSTSvyzNizDef = "ГОСТ 5781-82"
  End If
  FormSpecRost.TextBoxGOSTSvyzNizDef = psGOSTSvyzNizDef
  psGOSTSetokDef = oIni.GetFile("Настройки", "Норма арматуры сеток")
  If psGOSTSetokDef = "" Then
    psGOSTSetokDef = "ГОСТ 5781-82"
  End If
  FormSpecRost.TextBoxGOSTSetokDef = psGOSTSetokDef
  psGOSTDopStergDef = oIni.GetFile("Настройки", "Норма доп.стержней")
  If psGOSTDopStergDef = "" Then
    psGOSTDopStergDef = "ГОСТ 5781-82"
  End If
  FormSpecRost.TextBoxGOSTDopStergDef = psGOSTDopStergDef
  psGOSTShpilekDef = oIni.GetFile("Настройки", "Норма шпилек")
  If psGOSTShpilekDef = "" Then
    psGOSTShpilekDef = "ГОСТ 5781-82"
  End If
  FormSpecRost.TextBoxGOSTShpilekDef = psGOSTShpilekDef
  'TagString МаркиК
  psMarkaKTag = oIni.GetFile("Настройки", "Tag атрибута маркиК")
  If psMarkaKTag = "" Then
    psMarkaKTag = "МаркаК"
  End If
  FormSpecRost.TextBoxMarkaKTag = psMarkaKTag
  'галка расчета по МаркеК
  sValue = oIni.GetFile("Настройки", "Расчет по МаркеК")
  If sValue = "" Then
    pbMarkaKValue = False
  Else
    If sValue = "true" Then
      pbMarkaKValue = True
    Else
      pbMarkaKValue = False
    End If
  End If
  FormSpecRost.CheckBoxMarkaK.Value = pbMarkaKValue
  
  'Для расчета связевых стержней, Шир сеч - b
  piLenSvyzB = Val(oIni.GetFile("Настройки", "Суммарный защитный слой связевых стержней"))
  If piLenSvyzB = 0 Then
    piLenSvyzB = 20
  End If
  FormSpecRost.TextBoxLenSvyzB = piLenSvyzB
  'для кирпички
  piLenSvyzBK = Val(oIni.GetFile("Настройки", "Суммарный защитный слой связевых стержней К"))
  If piLenSvyzBK = 0 Then
    piLenSvyzBK = 50
  End If
  FormSpecRost.TextBoxLenSvyzBK = piLenSvyzBK
  
  'записываем год :)
  FormSpecRost.TextBoxYear = Year(Date) & "г."
  
  'считываем параметры простр.каркасов для номеров сеченирй
  'секция = Параметры простр каркасов
  'ключ = имени переменной
  'значение вида =ЗначениеДляNSech;ЗначениеДляNSech;...
  'номера сечений
  sValue = oIni.GetFile("Параметры сечений простр каркасов", "Номер сечения")
  GetAsNSechDef sValue
  sValue = oIni.GetFile("Параметры сечений простр каркасов", "Ширина сечения")
  GetArrayIntDef sValue, "Ширина сечения", True
  sValue = oIni.GetFile("Параметры сечений простр каркасов", "Высота ростверка")
  GetArrayIntDef sValue, "Высота ростверка", True
  sValue = oIni.GetFile("Параметры сечений простр каркасов", "Шаг верхней связевой")
  GetArrayIntDef sValue, "Шаг верхней связевой", True
  sValue = oIni.GetFile("Параметры сечений простр каркасов", "Шаг нижней связевой")
  GetArrayIntDef sValue, "Шаг нижней связевой", True
  sValue = oIni.GetFile("Параметры сечений простр каркасов", "Диаметр верхней связевой")
  GetArrayIntDef sValue, "Диаметр верхней связевой", True
  sValue = oIni.GetFile("Параметры сечений простр каркасов", "Диаметр нижней связевой")
  GetArrayIntDef sValue, "Диаметр нижней связевой", True
  sValue = oIni.GetFile("Параметры сечений простр каркасов", "Защ.слой нижний")
  GetArrayIntDef sValue, "Защ.слой нижний", True
  sValue = oIni.GetFile("Параметры сечений простр каркасов", "Защ.слой верхний")
  GetArrayIntDef sValue, "Защ.слой верхний", True
  sValue = oIni.GetFile("Параметры сечений простр каркасов", "Признак усиления")
  GetArrayBolUs sValue
  sValue = oIni.GetFile("Параметры сечений простр каркасов", "Ширина усиления")
  GetArrayIntDef sValue, "Ширина усиления", True
  sValue = oIni.GetFile("Параметры сечений простр каркасов", "Шаг верхней усиливающей")
  GetArrayIntDef sValue, "Шаг верхней усиливающей", True
  sValue = oIni.GetFile("Параметры сечений простр каркасов", "Шаг нижней усиливающей")
  GetArrayIntDef sValue, "Шаг нижней усиливающей", True
  sValue = oIni.GetFile("Параметры сечений простр каркасов", "Диаметр верхней усиливающей")
  GetArrayIntDef sValue, "Диаметр верхней усиливающей", True
  sValue = oIni.GetFile("Параметры сечений простр каркасов", "Диаметр нижней усиливающей")
  GetArrayIntDef sValue, "Диаметр нижней усиливающей", True
  sValue = oIni.GetFile("Параметры сечений простр каркасов", "Класс верхней усиливающей")
  GetArrayStringDef sValue, "Класс верхней усиливающей", True
  sValue = oIni.GetFile("Параметры сечений простр каркасов", "Класс нижней усиливающей")
  GetArrayStringDef sValue, "Класс нижней усиливающей", True
  sValue = oIni.GetFile("Параметры сечений простр каркасов", "Норма верхней усиливающей")
  GetArrayStringDef sValue, "Норма верхней усиливающей", True
  sValue = oIni.GetFile("Параметры сечений простр каркасов", "Норма нижней усиливающей")
  GetArrayStringDef sValue, "Норма нижней усиливающей", True
  sValue = oIni.GetFile("Параметры сечений простр каркасов", "Класс верхней")
  GetArrayStringDef sValue, "Класс верхней", True
  sValue = oIni.GetFile("Параметры сечений простр каркасов", "Класс нижней")
  GetArrayStringDef sValue, "Класс нижней", True
  sValue = oIni.GetFile("Параметры сечений простр каркасов", "Класс поперечной")
  GetArrayStringDef sValue, "Класс поперечной", True
  sValue = oIni.GetFile("Параметры сечений простр каркасов", "Класс верхней связевой")
  GetArrayStringDef sValue, "Класс верхней связевой", True
  sValue = oIni.GetFile("Параметры сечений простр каркасов", "Класс нижней связевой")
  GetArrayStringDef sValue, "Класс нижней связевой", True
  sValue = oIni.GetFile("Параметры сечений простр каркасов", "Норма верхней")
  GetArrayStringDef sValue, "Норма верхней", True
  sValue = oIni.GetFile("Параметры сечений простр каркасов", "Норма нижней")
  GetArrayStringDef sValue, "Норма нижней", True
  sValue = oIni.GetFile("Параметры сечений простр каркасов", "Норма поперечной")
  GetArrayStringDef sValue, "Норма поперечной", True
  sValue = oIni.GetFile("Параметры сечений простр каркасов", "Норма верхней связевой")
  GetArrayStringDef sValue, "Норма верхней связевой", True
  sValue = oIni.GetFile("Параметры сечений простр каркасов", "Норма нижней связевой")
  GetArrayStringDef sValue, "Норма нижней связевой", True
  
  'высота ростверка для первого сечения
  iHeightRostDef = aiHeightRostDef(0)
  'защитный слой
  iZachBetNizDef = aiZachBetNizDef(0)
  iZachBetVerhDef = aiZachBetVerhDef(0)
  
  'параметры плоских сечений
  sValue = oIni.GetFile("Параметры сечений плоских каркасов", "Номер сечения")
  GetAsNSechPlosDef sValue
  sValue = oIni.GetFile("Параметры сечений плоских каркасов", "Ширина сечения")
  GetArrayIntDef sValue, "Ширина сечения", False
  sValue = oIni.GetFile("Параметры сечений плоских каркасов", "Кол-во каркасов в сечении")
  GetArrayIntDef sValue, "Кол-во каркасов в сечении", False
  sValue = oIni.GetFile("Параметры сечений плоских каркасов", "Диаметр верхней связевой арматуры")
  GetArrayIntDef sValue, "Диаметр верхней связевой арматуры", False
  sValue = oIni.GetFile("Параметры сечений плоских каркасов", "Диаметр нижней связевой арматуры")
  GetArrayIntDef sValue, "Диаметр нижней связевой арматуры", False
  sValue = oIni.GetFile("Параметры сечений плоских каркасов", "Шаг верхней связевой арматуры")
  GetArrayIntDef sValue, "Шаг верхней связевой арматуры", False
  sValue = oIni.GetFile("Параметры сечений плоских каркасов", "Шаг нижней связевой арматуры")
  GetArrayIntDef sValue, "Шаг нижней связевой арматуры", False
  sValue = oIni.GetFile("Параметры сечений плоских каркасов", "Класс верхней связевой арматуры")
  GetArrayStringDef sValue, "Класс верхней связевой арматуры", False
  sValue = oIni.GetFile("Параметры сечений плоских каркасов", "Класс нижней связевой арматуры")
  GetArrayStringDef sValue, "Класс нижней связевой арматуры", False
  sValue = oIni.GetFile("Параметры сечений плоских каркасов", "ГОСТ верхней связевой арматуры")
  GetArrayStringDef sValue, "ГОСТ верхней связевой арматуры", False
  sValue = oIni.GetFile("Параметры сечений плоских каркасов", "ГОСТ нижней связевой арматуры")
  GetArrayStringDef sValue, "ГОСТ нижней связевой арматуры", False
  
  'параметры перепадов
  piDiamSter1Perepada = Val(oIni.GetFile("Перепады", "piDiamSter1Perepada"))
  If Functions.ProvDiamStandard(piDiamSter1Perepada) = False Then
    piDiamSter1Perepada = "12"
  End If
  FormSpecRost.TextBoxDiamSter1Perepada = piDiamSter1Perepada
  piDiamSter2Perepada = Val(oIni.GetFile("Перепады", "piDiamSter2Perepada"))
  If Functions.ProvDiamStandard(piDiamSter2Perepada) = False Then
    piDiamSter2Perepada = "12"
  End If
  FormSpecRost.TextBoxDiamSter2Perepada = piDiamSter2Perepada
  piDiamSter3Perepada = Val(oIni.GetFile("Перепады", "piDiamSter3Perepada"))
  If Functions.ProvDiamStandard(piDiamSter3Perepada) = False Then
    piDiamSter3Perepada = "10"
  End If
  FormSpecRost.TextBoxDiamSter3Perepada = piDiamSter3Perepada
  piDiamSter4Perepada = Val(oIni.GetFile("Перепады", "piDiamSter4Perepada"))
  If Functions.ProvDiamStandard(piDiamSter4Perepada) = False Then
    piDiamSter4Perepada = "8"
  End If
  FormSpecRost.TextBoxDiamSter4Perepada = piDiamSter4Perepada
  psKlassSter1Perepada = oIni.GetFile("Перепады", "psKlassSter1Perepada")
  If psKlassSter1Perepada = "" Then
    psKlassSter1Perepada = "A-III"
  End If
  FormSpecRost.TextBoxKlassSter1Perepada = psKlassSter1Perepada
  psKlassSter2Perepada = oIni.GetFile("Перепады", "psKlassSter2Perepada")
  If psKlassSter2Perepada = "" Then
    psKlassSter2Perepada = "A-III"
  End If
  FormSpecRost.TextBoxKlassSter2Perepada = psKlassSter2Perepada
  psKlassSter3Perepada = oIni.GetFile("Перепады", "psKlassSter3Perepada")
  If psKlassSter3Perepada = "" Then
    psKlassSter3Perepada = "A-III"
  End If
  FormSpecRost.TextBoxKlassSter3Perepada = psKlassSter3Perepada
  psKlassSter4Perepada = oIni.GetFile("Перепады", "psKlassSter4Perepada")
  If psKlassSter4Perepada = "" Then
    psKlassSter4Perepada = "A-I"
  End If
  FormSpecRost.TextBoxKlassSter4Perepada = psKlassSter4Perepada
  psGostSter1Perepada = oIni.GetFile("Перепады", "psGostSter1Perepada")
  If psGostSter1Perepada = "" Then
    psGostSter1Perepada = "ГОСТ 5781-82"
  End If
  FormSpecRost.TextBoxGostSter1Perepada = psGostSter1Perepada
  psGostSter2Perepada = oIni.GetFile("Перепады", "psGostSter2Perepada")
  If psGostSter2Perepada = "" Then
    psGostSter2Perepada = "ГОСТ 5781-82"
  End If
  FormSpecRost.TextBoxGostSter2Perepada = psGostSter2Perepada
  psGostSter3Perepada = oIni.GetFile("Перепады", "psGostSter3Perepada")
  If psGostSter3Perepada = "" Then
    psGostSter3Perepada = "ГОСТ 5781-82"
  End If
  FormSpecRost.TextBoxGostSter3Perepada = psGostSter3Perepada
  psGostSter4Perepada = oIni.GetFile("Перепады", "psGostSter4Perepada")
  If psGostSter4Perepada = "" Then
    psGostSter4Perepada = "ГОСТ 5781-82"
  End If
  FormSpecRost.TextBoxGostSter4Perepada = psGostSter4Perepada
  
  'Исходные данные (заполнение штампа и обложек)
  On Error Resume Next
  pForShtampShifr = oIni.GetFile("ИсходныеДанные", "pForShtampShifr")
  pForShtampBS = CBool(oIni.GetFile("ИсходныеДанные", "pForShtampBS"))
  pForShtampNPart = oIni.GetFile("ИсходныеДанные", "pForShtampNPart")
  pForShtampAdres = oIni.GetFile("ИсходныеДанные", "pForShtampAdres")
  pForShtampNaimenObject = oIni.GetFile("ИсходныеДанные", "pForShtampNaimenObject")
  pForShtampPost1 = oIni.GetFile("ИсходныеДанные", "pForShtampPost1")
  pForShtampPost2 = oIni.GetFile("ИсходныеДанные", "pForShtampPost2")
  pForShtampPost3 = oIni.GetFile("ИсходныеДанные", "pForShtampPost3")
  pForShtampPost4 = oIni.GetFile("ИсходныеДанные", "pForShtampPost4")
  pForShtampPost5 = oIni.GetFile("ИсходныеДанные", "pForShtampPost5")
  pForShtampPost6 = oIni.GetFile("ИсходныеДанные", "pForShtampPost6")
  pForShtampFam1 = oIni.GetFile("ИсходныеДанные", "pForShtampFam1")
  pForShtampFam2 = oIni.GetFile("ИсходныеДанные", "pForShtampFam2")
  pForShtampFam3 = oIni.GetFile("ИсходныеДанные", "pForShtampFam3")
  pForShtampFam4 = oIni.GetFile("ИсходныеДанные", "pForShtampFam4")
  pForShtampFam5 = oIni.GetFile("ИсходныеДанные", "pForShtampFam5")
  pForShtampFam6 = oIni.GetFile("ИсходныеДанные", "pForShtampFam6")
  pForSgtampChkBox1ForTitulPost = CBool(oIni.GetFile("ИсходныеДанные", "pForSgtampChkBox1ForTitulPost"))
  pForSgtampChkBox2ForTitulPost = CBool(oIni.GetFile("ИсходныеДанные", "pForSgtampChkBox2ForTitulPost"))
  pForSgtampChkBox3ForTitulPost = CBool(oIni.GetFile("ИсходныеДанные", "pForSgtampChkBox3ForTitulPost"))
  pForSgtampChkBox1ForShtamp = CBool(oIni.GetFile("ИсходныеДанные", "pForSgtampChkBox1ForShtamp"))
  pForSgtampChkBox2ForShtamp = CBool(oIni.GetFile("ИсходныеДанные", "pForSgtampChkBox2ForShtamp"))
  pForSgtampChkBox3ForShtamp = CBool(oIni.GetFile("ИсходныеДанные", "pForSgtampChkBox3ForShtamp"))
  pForSgtampChkBox4ForShtamp = CBool(oIni.GetFile("ИсходныеДанные", "pForSgtampChkBox4ForShtamp"))
  pForSgtampChkBox5ForShtamp = CBool(oIni.GetFile("ИсходныеДанные", "pForSgtampChkBox5ForShtamp"))
  pForSgtampChkBox6ForShtamp = CBool(oIni.GetFile("ИсходныеДанные", "pForSgtampChkBox6ForShtamp"))
  'заполнение формы вкладки Исходные данные
  FormSpecRost.TextBoxShifr = pForShtampShifr
  FormSpecRost.CheckBoxShifrBS.Value = pForShtampBS
  FormSpecRost.TextBoxNpart = pForShtampNPart
  FormSpecRost.TextBoxAdres = pForShtampAdres
  FormSpecRost.TextBoxNaimenDoma = pForShtampNaimenObject
  FormSpecRost.TextBoxPost1 = pForShtampPost1
  FormSpecRost.TextBoxPost2 = pForShtampPost2
  FormSpecRost.TextBoxPost3 = pForShtampPost3
  FormSpecRost.TextBoxPost4 = pForShtampPost4
  FormSpecRost.TextBoxPost5 = pForShtampPost5
  FormSpecRost.TextBoxPost6 = pForShtampPost6
  FormSpecRost.TextBoxFam1 = pForShtampFam1
  FormSpecRost.TextBoxFam2 = pForShtampFam2
  FormSpecRost.TextBoxFam3 = pForShtampFam3
  FormSpecRost.TextBoxFam4 = pForShtampFam4
  FormSpecRost.TextBoxFam5 = pForShtampFam5
  FormSpecRost.TextBoxFam6 = pForShtampFam6
  FormSpecRost.cbShtampTitul1 = pForSgtampChkBox1ForTitulPost
  FormSpecRost.cbShtampTitul2 = pForSgtampChkBox2ForTitulPost
  FormSpecRost.cbShtampTitul3 = pForSgtampChkBox3ForTitulPost
  FormSpecRost.cbShtamp1 = pForSgtampChkBox1ForShtamp
  FormSpecRost.cbShtamp2 = pForSgtampChkBox2ForShtamp
  FormSpecRost.cbShtamp3 = pForSgtampChkBox3ForShtamp
  FormSpecRost.cbShtamp4 = pForSgtampChkBox4ForShtamp
  FormSpecRost.cbShtamp5 = pForSgtampChkBox5ForShtamp
  FormSpecRost.cbShtamp6 = pForSgtampChkBox6ForShtamp
  Functions.VerifyCheckBoxForShtamp 'проверка кол-ва галок для фамилий Штампов на вкладке Исходных данных
  
  'Загрузка расчетов в комбобокс
'  LoadRaschetyFromIni
  
End Sub

Public Sub SaveProsKarParamSech(sNSehToSave As String)
  'сохранение параметров(текущих значений полей) для текущего номера сечения
  Dim i As Integer
  Dim bolYes As Boolean
  Dim intBound As Integer
  
  If FormSpecRost.CheckBoxMarkaK.Value = True Then
'    Exit Sub
  End If
  
  intBound = UBound(asNSechDef)
  
  For i = 0 To intBound
    If asNSechDef(i) = sNSehToSave Then
      'для этого индекса i запоминаем значения полей
      bolYes = True
      Exit For
    End If
  Next
  
  If bolYes = False Then
    i = intBound + 1
    ReDim Preserve asNSechDef(i)
    ReDim Preserve aiLenSechDef(i)
    ReDim Preserve aiHeightRostDef(i)
    ReDim Preserve aiShagSvyzNizArmDef(i)
    ReDim Preserve aiShagSvyzVerhArmDef(i)
    ReDim Preserve aiDiamSvyzNizArmDef(i)
    ReDim Preserve aiDiamSvyzVerhArmDef(i)
    ReDim Preserve aiZachBetNizDef(i)
    ReDim Preserve aiZachBetVerhDef(i)
    ReDim Preserve abolUsilenie(i)
    ReDim Preserve aiUsLenSechDef(i)
    ReDim Preserve aiUsDiamNizArmDef(i)
    ReDim Preserve aiUsDiamVerhArmDef(i)
    ReDim Preserve aiUsShagVerhArmDef(i)
    ReDim Preserve aiUsShagNizArmDef(i)
    ReDim Preserve asUsKlassNizArmDef(i)
    ReDim Preserve asUsKlassVerhArmDef(i)
    ReDim Preserve asUsGOSTNizArmDef(i)
    ReDim Preserve asUsGOSTVerhArmDef(i)
    ReDim Preserve asKlassVerhArmDef(i)
    ReDim Preserve asKlassNizArmDef(i)
    ReDim Preserve asKlassPopArmDef(i)
    ReDim Preserve asKlassSvyzNizArmDef(i)
    ReDim Preserve asKlassSvyzVerhArmDef(i)
    ReDim Preserve asGOSTNizArmDef(i)
    ReDim Preserve asGOSTVerhArmDef(i)
    ReDim Preserve asGOSTPopArmDef(i)
    ReDim Preserve asGOSTSvyzNizArmDef(i)
    ReDim Preserve asGOSTSvyzVerhArmDef(i)
  End If
  
  'запоминаем значения
  asNSechDef(i) = sNSehToSave
  'заполняем поля формы
    aiLenSechDef(i) = FormSpecRost.TextBoxLenSech
    'если высота ростверка задана в имени каркаса (в скобках - "(6)")
    aiHeightRostDef(i) = FormSpecRost.TextBoxHeightRost
    
    aiShagSvyzNizArmDef(i) = FormSpecRost.TextBoxShagNizSvyzSter
    aiShagSvyzVerhArmDef(i) = FormSpecRost.TextBoxShagVerhSvyzSter
    aiDiamSvyzNizArmDef(i) = FormSpecRost.TextBoxDiamNizSvyzSter
    aiDiamSvyzVerhArmDef(i) = FormSpecRost.TextBoxDiamVerhSvyzSter
    aiZachBetNizDef(i) = FormSpecRost.TextBoxNizZachBet
    aiZachBetVerhDef(i) = FormSpecRost.TextBoxVerhZachBet
    'параметры для усиления
    abolUsilenie(i) = FormSpecRost.CheckBoxUsilenie.Value
    If abolUsilenie(i) = True Then
      aiUsLenSechDef(i) = FormSpecRost.TextBoxUsLenSech
      aiUsDiamNizArmDef(i) = FormSpecRost.TextBoxUsDiamNizArm
      aiUsDiamVerhArmDef(i) = FormSpecRost.TextBoxUsDiamVerhArm
      aiUsShagVerhArmDef(i) = FormSpecRost.TextBoxUsShagVerhArm
      aiUsShagNizArmDef(i) = FormSpecRost.TextBoxUsShagNizArm
      asUsKlassNizArmDef(i) = FormSpecRost.TextBoxUsKlassNizArm
      asUsKlassVerhArmDef(i) = FormSpecRost.TextBoxUsKlassVerhArm
      asUsGOSTNizArmDef(i) = FormSpecRost.TextBoxUsGOSTNizArm
      asUsGOSTVerhArmDef(i) = FormSpecRost.TextBoxUsGOSTVerhArm
    End If
    asKlassVerhArmDef(i) = FormSpecRost.TextBoxKlassVerhArm
    asKlassNizArmDef(i) = FormSpecRost.TextBoxKlassNizArm
    asKlassPopArmDef(i) = FormSpecRost.TextBoxKlassPopArm
    asKlassSvyzNizArmDef(i) = FormSpecRost.TextBoxKlassSvyzNizArm
    asKlassSvyzVerhArmDef(i) = FormSpecRost.TextBoxKlassSvyzVerhArm
    asGOSTNizArmDef(i) = FormSpecRost.TextBoxGOSTNizArm
    asGOSTVerhArmDef(i) = FormSpecRost.TextBoxGOSTVerhArm
    asGOSTPopArmDef(i) = FormSpecRost.TextBoxGOSTPopArm
    asGOSTSvyzNizArmDef(i) = FormSpecRost.TextBoxGOSTSvyzNizArm
    asGOSTSvyzVerhArmDef(i) = FormSpecRost.TextBoxGOSTSvyzVerhArm
  
End Sub

Public Sub SavePlosKarParamSech()
  'сохранение параметров(текущих значений полей) для текущего номера сечения плоских каркасов
  Dim sNSehToSave As String
  Dim i As Integer
  Dim bolYes As Boolean
  Dim intBound As Integer
  
  sNSehToSave = FormSpecRost.TextBoxNSechPlosKar
  
  intBound = UBound(asNSechPlosDef)
  
  For i = 0 To intBound
    If asNSechPlosDef(i) = sNSehToSave Then
      'для этого индекса i запоминаем значения полей
      bolYes = True
      Exit For
    End If
  Next
  
  If bolYes = False Then
    i = intBound + 1
    ReDim Preserve asNSechPlosDef(i)
    ReDim Preserve aiLenSechPlosDef(i)
    ReDim Preserve aiKolInSechPlosDef(i)
    ReDim Preserve aiDiamVerhSvyzPlosDef(i)
    ReDim Preserve aiDiamNizSvyzPlosDef(i)
    ReDim Preserve aiShagVerhSvyzPlosDef(i)
    ReDim Preserve aiShagNizSvyzPlosDef(i)
    ReDim Preserve asKlassVerhSvyzPlosDef(i)
    ReDim Preserve asKlassNizSvyzPlosDef(i)
    ReDim Preserve asGOSTVerhSvyzPlosDef(i)
    ReDim Preserve asGOSTNizSvyzPlosDef(i)
  End If
  
  'запоминаем значения
  asNSechPlosDef(i) = sNSehToSave
  'заполняем поля формы
  aiLenSechPlosDef(i) = FormSpecRost.TextBoxWPlosKar
  aiKolInSechPlosDef(i) = FormSpecRost.TextBoxn1PlosKar
  aiDiamVerhSvyzPlosDef(i) = FormSpecRost.TextBoxFPlosKar
  aiDiamNizSvyzPlosDef(i) = FormSpecRost.TextBoxF1PlosKar
  aiShagVerhSvyzPlosDef(i) = FormSpecRost.TextBoxSPlosKar
  aiShagNizSvyzPlosDef(i) = FormSpecRost.TextBoxS1PlosKar
  asKlassVerhSvyzPlosDef(i) = FormSpecRost.TextBoxKlassSvyzPlosKar
  asKlassNizSvyzPlosDef(i) = FormSpecRost.TextBoxKlass1SvyzPlosKar
  asGOSTVerhSvyzPlosDef(i) = FormSpecRost.TextBoxGOSTSvyzVerhPlosKar
  asGOSTNizSvyzPlosDef(i) = FormSpecRost.TextBoxGOSTSvyzNizPlosKar
  
End Sub

Public Sub LoadProsKarParamSech(sNSechForLoad As String)
  'заполнение полей параметров простр. каркаса для текущего номера сечения
  
'  Dim sNSechForLoad As String 'номер сечения для которого нужно произвести загрузку
  Dim bolYes As Boolean
  Dim bol0Sech As Boolean
  Dim bol1Sech As Boolean
  Dim iIndex0Sech As Integer
  Dim iIndex1Sech As Integer
  Dim i As Integer
  
  '1 определить номер сечения для которого нужно загрузить парасетры (если они были сохранены)
  'причем номер сечения - это строка а не число!!! (может быть 5а)
'  sNSechForLoad = FormSpecRost.TextBoxNSech
  
  '2 Находим его в массиве сохраненных сечений
  For i = 0 To UBound(asNSechDef)
    If asNSechDef(i) = "0" Then
      iIndex0Sech = i
      bol0Sech = True
    End If
    If asNSechDef(i) = "1" Then
      iIndex1Sech = i
      bol1Sech = True
    End If
    If asNSechDef(i) = sNSechForLoad Then
      'для этого индекса i, заполняем поля из переменных
      'для кирпички не нужно применять сохраненные в ини значения (т.к. там сечения всегда разные)
      If FormSpecRost.CheckBoxMarkaK.Value = False Then
        bolYes = True
      End If
      Exit For
    End If
  Next
  
  If bolYes = False Then
    'считываем значения по-умолчанию
    If bol0Sech = True Or bol1Sech = True Then
      If bol0Sech = True Then
        i = iIndex0Sech
      Else
        i = iIndex1Sech
      End If
    Else
          'заполняем прямыми значениями
          FormSpecRost.TextBoxLenSech = 500
        'если высота ростверка задана в имени каркаса (в скобках - "(6)")
        If FormSpecRost.TextBoxHeightRost.Enabled = True Then
          FormSpecRost.TextBoxHeightRost = 400
        End If
        
        FormSpecRost.TextBoxShagNizSvyzSter = 300
        FormSpecRost.TextBoxShagVerhSvyzSter = 300
        FormSpecRost.TextBoxDiamNizSvyzSter = 8
        FormSpecRost.TextBoxDiamVerhSvyzSter = 8
        FormSpecRost.TextBoxNizZachBet = 80
        FormSpecRost.TextBoxVerhZachBet = 40
        'параметры для усиления
        'ПО умолчанию false
          FormSpecRost.CheckBoxUsilenie.Value = False
          FormSpecRost.TextBoxUsLenSech = 1050
          FormSpecRost.TextBoxUsDiamNizArm = 8
          FormSpecRost.TextBoxUsDiamVerhArm = 8
          FormSpecRost.TextBoxUsShagNizArm = 300
          FormSpecRost.TextBoxUsShagVerhArm = 300
          FormSpecRost.TextBoxUsKlassNizArm = "A-III"
          FormSpecRost.TextBoxUsKlassVerhArm = "A-III"
          FormSpecRost.TextBoxUsGOSTNizArm = "ГОСТ 5781-82"
          FormSpecRost.TextBoxUsGOSTVerhArm = "ГОСТ 5781-82"
          
        FormSpecRost.TextBoxKlassVerhArm = "A-III"
        FormSpecRost.TextBoxKlassNizArm = "A-III"
        FormSpecRost.TextBoxKlassPopArm = "A-III"
        FormSpecRost.TextBoxKlassSvyzNizArm = "A-III"
        FormSpecRost.TextBoxKlassSvyzVerhArm = "A-III"
        FormSpecRost.TextBoxGOSTNizArm = "ГОСТ 5781-82"
        FormSpecRost.TextBoxGOSTVerhArm = "ГОСТ 5781-82"
        FormSpecRost.TextBoxGOSTPopArm = "ГОСТ 5781-82"
        FormSpecRost.TextBoxGOSTSvyzNizArm = "ГОСТ 5781-82"
        FormSpecRost.TextBoxGOSTSvyzVerhArm = "ГОСТ 5781-82"
      Exit Sub
    End If
  End If
  
  'считываем значения по-умолчанию с настроек
    'заполняем поля формы
    FormSpecRost.TextBoxLenSech = aiLenSechDef(i)
    'если высота ростверка задана в имени каркаса (в скобках - "(6)")
    If FormSpecRost.TextBoxHeightRost.Enabled = True Then
      FormSpecRost.TextBoxHeightRost = aiHeightRostDef(i)
    End If
    
    FormSpecRost.TextBoxShagNizSvyzSter = aiShagSvyzNizArmDef(i)
    FormSpecRost.TextBoxShagVerhSvyzSter = aiShagSvyzVerhArmDef(i)
    FormSpecRost.TextBoxDiamNizSvyzSter = aiDiamSvyzNizArmDef(i)
    FormSpecRost.TextBoxDiamVerhSvyzSter = aiDiamSvyzVerhArmDef(i)
    FormSpecRost.TextBoxNizZachBet = aiZachBetNizDef(i)
    FormSpecRost.TextBoxVerhZachBet = aiZachBetVerhDef(i)
    'параметры для усиления
    If abolUsilenie(i) = True Then
      FormSpecRost.CheckBoxUsilenie.Value = True
      FormSpecRost.TextBoxUsLenSech = aiUsLenSechDef(i)
      FormSpecRost.TextBoxUsDiamNizArm = aiUsDiamNizArmDef(i)
      FormSpecRost.TextBoxUsDiamVerhArm = aiUsDiamVerhArmDef(i)
      FormSpecRost.TextBoxUsShagNizArm = aiUsShagNizArmDef(i)
      FormSpecRost.TextBoxUsShagVerhArm = aiUsShagVerhArmDef(i)
      FormSpecRost.TextBoxUsKlassNizArm = asUsKlassNizArmDef(i)
      FormSpecRost.TextBoxUsKlassVerhArm = asUsKlassVerhArmDef(i)
      FormSpecRost.TextBoxUsGOSTNizArm = asUsGOSTNizArmDef(i)
      FormSpecRost.TextBoxUsGOSTVerhArm = asUsGOSTVerhArmDef(i)
    Else
      FormSpecRost.CheckBoxUsilenie.Value = False
    End If
    FormSpecRost.TextBoxKlassVerhArm = asKlassVerhArmDef(i)
    FormSpecRost.TextBoxKlassNizArm = asKlassNizArmDef(i)
    FormSpecRost.TextBoxKlassPopArm = asKlassPopArmDef(i)
    FormSpecRost.TextBoxKlassSvyzNizArm = asKlassSvyzNizArmDef(i)
    FormSpecRost.TextBoxKlassSvyzVerhArm = asKlassSvyzVerhArmDef(i)
    FormSpecRost.TextBoxGOSTNizArm = asGOSTNizArmDef(i)
    FormSpecRost.TextBoxGOSTVerhArm = asGOSTVerhArmDef(i)
    FormSpecRost.TextBoxGOSTPopArm = asGOSTPopArmDef(i)
    FormSpecRost.TextBoxGOSTSvyzNizArm = asGOSTSvyzNizArmDef(i)
    FormSpecRost.TextBoxGOSTSvyzVerhArm = asGOSTSvyzVerhArmDef(i)
  
End Sub
Public Sub LoadPlosKarParamSech()
  'заполнение полей параметров сечения плоского каркаса для текущего номера сечения
  
  Dim sNSechForLoad As String 'номер сечения для которого нужно произвести загрузку
  Dim bolYes As Boolean
  Dim bol0Sech As Boolean
  Dim iIndex0Sech As Integer
  Dim i As Integer
  
  '1 определить номер сечения для которого нужно загрузить парасетры (если они были сохранены)
  'причем номер сечения - это строка а не число!!! (может быть 5а)
  sNSechForLoad = FormSpecRost.TextBoxNSechPlosKar
  
  '2 Находим его в массиве сохраненных сечений
  For i = 0 To UBound(asNSechPlosDef)
    If asNSechPlosDef(i) = "0" Then
      iIndex0Sech = i
      bol0Sech = True
    End If
    If asNSechPlosDef(i) = sNSechForLoad Then
      'для этого индекса i, заполняем поля из переменных
      bolYes = True
      Exit For
    End If
  Next
  If bolYes = False Then
    'считываем значения поумолчанию для первого каркаса
    If bol0Sech = True Then
      i = iIndex0Sech
    Else
        'заполняем прямыми значениями
        FormSpecRost.TextBoxWPlosKar = 500
        FormSpecRost.TextBoxn1PlosKar = 2
        FormSpecRost.TextBoxSPlosKar = 300
        FormSpecRost.TextBoxFPlosKar = 8
        FormSpecRost.TextBoxKlassSvyzPlosKar = psKlassSvyzVerhDef
        FormSpecRost.TextBoxGOSTSvyzVerhPlosKar = psGOSTSvyzVerhDef
        FormSpecRost.TextBoxS1PlosKar = 300
        FormSpecRost.TextBoxF1PlosKar = 8
        FormSpecRost.TextBoxKlass1SvyzPlosKar = psKlassSvyzNizDef
        FormSpecRost.TextBoxGOSTSvyzNizPlosKar = psGOSTSvyzNizDef
      Exit Sub
    End If
  End If
  
  'считываем значения по-умолчанию с настроек
  'заполняем поля формы
  FormSpecRost.TextBoxWPlosKar = aiLenSechPlosDef(i)
  FormSpecRost.TextBoxn1PlosKar = aiKolInSechPlosDef(i)
  FormSpecRost.TextBoxSPlosKar = aiShagVerhSvyzPlosDef(i)
  FormSpecRost.TextBoxFPlosKar = aiDiamVerhSvyzPlosDef(i)
  FormSpecRost.TextBoxKlassSvyzPlosKar = asKlassVerhSvyzPlosDef(i)
  FormSpecRost.TextBoxGOSTSvyzVerhPlosKar = asGOSTVerhSvyzPlosDef(i)
  FormSpecRost.TextBoxS1PlosKar = aiShagNizSvyzPlosDef(i)
  FormSpecRost.TextBoxF1PlosKar = aiDiamNizSvyzPlosDef(i)
  FormSpecRost.TextBoxKlass1SvyzPlosKar = asKlassNizSvyzPlosDef(i)
  FormSpecRost.TextBoxGOSTSvyzNizPlosKar = asGOSTNizSvyzPlosDef(i)
  
End Sub

Private Sub Class_Initialize()
  'заполняем значения переменных
End Sub

Private Function GetAsNSechDef(sValue As String)
  'преобразование строки номеров сечений из ини в массив строк номеров сечений
  
  Dim intLenStr As Integer
  Dim intDec As Integer
  Dim i As Integer
  
  ReDim asNSechDef(0)
  
  If sValue = "" Then
    asNSechDef(0) = "1"
    Exit Function
  End If
  
  intDec = InStr(sValue, ";")
  If intDec = 0 Then
    asNSechDef(0) = sValue
    Exit Function
  End If
  
  intLenStr = Len(sValue)
  Do
    ReDim Preserve asNSechDef(i)
    asNSechDef(i) = Left(sValue, intDec - 1)
    intLenStr = intLenStr - intDec
    sValue = Right(sValue, intLenStr)
    intDec = InStr(sValue, ";")
    i = i + 1
  Loop Until intDec = 0
  
End Function
Private Function GetAsNSechPlosDef(sValue As String)
  'преобразование строки номеров сечений плоских каркасов из ини в массив строк номеров сечений
  
  Dim intLenStr As Integer
  Dim intDec As Integer
  Dim i As Integer
  
  ReDim asNSechPlosDef(0)
  
  If sValue = "" Then
    asNSechPlosDef(0) = "3"
    Exit Function
  End If
  
  intDec = InStr(sValue, ";")
  If intDec = 0 Then
    asNSechPlosDef(0) = sValue
    Exit Function
  End If
  
  intLenStr = Len(sValue)
  Do
    ReDim Preserve asNSechPlosDef(i)
    asNSechPlosDef(i) = Left(sValue, intDec - 1)
    intLenStr = intLenStr - intDec
    sValue = Right(sValue, intLenStr)
    intDec = InStr(sValue, ";")
    i = i + 1
  Loop Until intDec = 0
  
End Function

Private Function GetArrayIntDef(sValue As String, sKey As String, bolProsOrPlosKar As Boolean)
  'преобразование строки значений параметра из ини для номеров сечений в массив значений
  
  Dim aiValue() As Integer
  Dim intLenStr As Integer
  Dim intDec As Integer
  Dim intUbound As Integer
  Dim i As Integer
  Dim intDefault As Integer
  
  If bolProsOrPlosKar = True Then
    Select Case sKey
      Case "Ширина сечения"
        intDefault = 500
      Case "Высота ростверка"
        intDefault = 400
      Case "Шаг верхней связевой"
        intDefault = 300
      Case "Шаг нижней связевой"
        intDefault = 300
      Case "Диаметр верхней связевой"
        intDefault = 8
      Case "Диаметр нижней связевой"
        intDefault = 8
      Case "Защ.слой нижний"
        intDefault = 80
      Case "Защ.слой верхний"
        intDefault = 40
      Case "Ширина усиления"
        intDefault = 1050
      Case "Шаг верхней усиливающей"
        intDefault = 300
      Case "Шаг нижней усиливающей"
        intDefault = 300
      Case "Диаметр верхней усиливающей"
        intDefault = 8
      Case "Диаметр нижней усиливающей"
        intDefault = 8
      Case Else
        MsgBox "Имя параметра простр каркаса не определен!"
        Exit Function
    End Select
    intUbound = UBound(asNSechDef)
  Else
    'для плоских
    Select Case sKey
      Case "Ширина сечения"
          intDefault = 500
      Case "Кол-во каркасов в сечении"
          intDefault = 1
      Case "Диаметр верхней связевой арматуры"
          intDefault = 8
      Case "Диаметр нижней связевой арматуры"
          intDefault = 8
      Case "Шаг верхней связевой арматуры"
          intDefault = 300
      Case "Шаг нижней связевой арматуры"
          intDefault = 300
    End Select
    intUbound = UBound(asNSechPlosDef)
  End If
  
  ReDim aiValue(intUbound)
  
  If sValue = "" Then
    For i = 0 To intUbound
      aiValue(i) = intDefault
    Next
    GoTo ExitHere
  End If
  
  intDec = InStr(sValue, ";")
  If intDec = 0 Then
    aiValue(0) = CInt(sValue)
    For i = 1 To intUbound
      aiValue(i) = intDefault
    Next
    GoTo ExitHere
  End If
  intLenStr = Len(sValue)
  Do
    aiValue(i) = Val(Left(sValue, intDec - 1))
    intLenStr = intLenStr - intDec
    sValue = Right(sValue, intLenStr)
    intDec = InStr(sValue, ";")
    i = i + 1
  Loop Until intDec = 0
  
  For i = 0 To intUbound
    If aiValue(i) = 0 Then aiValue(i) = intDefault
  Next
  
ExitHere:
  If bolProsOrPlosKar = True Then
    Select Case sKey
      Case "Ширина сечения"
        aiLenSechDef = aiValue
      Case "Высота ростверка"
        aiHeightRostDef = aiValue
      Case "Шаг верхней связевой"
        aiShagSvyzVerhArmDef = aiValue
      Case "Шаг нижней связевой"
        aiShagSvyzNizArmDef = aiValue
      Case "Диаметр верхней связевой"
        aiDiamSvyzVerhArmDef = aiValue
      Case "Диаметр нижней связевой"
        aiDiamSvyzNizArmDef = aiValue
      Case "Защ.слой нижний"
        aiZachBetNizDef = aiValue
      Case "Защ.слой верхний"
        aiZachBetVerhDef = aiValue
      Case "Ширина усиления"
        aiUsLenSechDef = aiValue
      Case "Шаг верхней усиливающей"
        aiUsShagVerhArmDef = aiValue
      Case "Шаг нижней усиливающей"
        aiUsShagNizArmDef = aiValue
      Case "Диаметр верхней усиливающей"
        aiUsDiamVerhArmDef = aiValue
      Case "Диаметр нижней усиливающей"
        aiUsDiamNizArmDef = aiValue
    End Select
  Else
    'для плоских
    Select Case sKey
      Case "Ширина сечения"
          aiLenSechPlosDef = aiValue
      Case "Кол-во каркасов в сечении"
          aiKolInSechPlosDef = aiValue
      Case "Диаметр верхней связевой арматуры"
          aiDiamVerhSvyzPlosDef = aiValue
      Case "Диаметр нижней связевой арматуры"
          aiDiamNizSvyzPlosDef = aiValue
      Case "Шаг верхней связевой арматуры"
          aiShagVerhSvyzPlosDef = aiValue
      Case "Шаг нижней связевой арматуры"
          aiShagNizSvyzPlosDef = aiValue
    End Select
  End If
  
End Function

Private Function GetStringArrayIntDef(sKey As String, bolProsOrPlos As Boolean) As String
  'преобразование массива значений в строку
  
  Dim aiValue() As Integer
  Dim i As Integer
  
  If bolProsOrPlos = True Then
    Select Case sKey
      Case "Ширина сечения"
        aiValue = aiLenSechDef
      Case "Высота ростверка"
        aiValue = aiHeightRostDef
      Case "Шаг верхней связевой"
        aiValue = aiShagSvyzVerhArmDef
      Case "Шаг нижней связевой"
        aiValue = aiShagSvyzNizArmDef
      Case "Диаметр верхней связевой"
        aiValue = aiDiamSvyzVerhArmDef
      Case "Диаметр нижней связевой"
        aiValue = aiDiamSvyzNizArmDef
      Case "Защ.слой нижний"
        aiValue = aiZachBetNizDef
      Case "Защ.слой верхний"
        aiValue = aiZachBetVerhDef
      Case "Ширина усиления"
        aiValue = aiUsLenSechDef
      Case "Шаг верхней усиливающей"
        aiValue = aiUsShagVerhArmDef
      Case "Шаг нижней усиливающей"
        aiValue = aiUsShagNizArmDef
      Case "Диаметр верхней усиливающей"
        aiValue = aiUsDiamVerhArmDef
      Case "Диаметр нижней усиливающей"
        aiValue = aiUsDiamNizArmDef
      Case Else
        MsgBox "Имя параметра простр каркаса не определен!"
        Exit Function
    End Select
  Else
    'для плоских
    Select Case sKey
      Case "Ширина сечения"
          aiValue = aiLenSechPlosDef
      Case "Кол-во каркасов в сечении"
          aiValue = aiKolInSechPlosDef
      Case "Диаметр верхней связевой арматуры"
          aiValue = aiDiamVerhSvyzPlosDef
      Case "Диаметр нижней связевой арматуры"
          aiValue = aiDiamNizSvyzPlosDef
      Case "Шаг верхней связевой арматуры"
          aiValue = aiShagVerhSvyzPlosDef
      Case "Шаг нижней связевой арматуры"
          aiValue = aiShagNizSvyzPlosDef
    End Select
  End If
    
  For i = 0 To UBound(aiValue)
    GetStringArrayIntDef = GetStringArrayIntDef & aiValue(i) & ";"
  Next
'  'убираем последний ";"
'  GetStringArrayIntDef = Left(GetStringArrayIntDef, Len(GetStringArrayIntDef) - 1)
  
End Function

Private Function GetStringArrayStrDef(sKey As String, bolProsOrPlos As Boolean) As String
  'преобразование массива значений в строку
  
  Dim asValue() As String
  Dim i As Integer
  
  If bolProsOrPlos = True Then
    Select Case sKey
      Case "Класс верхней усиливающей"
        asValue = asUsKlassVerhArmDef
      Case "Класс нижней усиливающей"
        asValue = asUsKlassNizArmDef
      Case "Класс верхней"
        asValue = asKlassVerhArmDef
      Case "Класс нижней"
        asValue = asKlassVerhArmDef
      Case "Класс поперечной"
        asValue = asKlassPopArmDef
      Case "Класс верхней связевой"
        asValue = asKlassSvyzVerhArmDef
      Case "Класс нижней связевой"
        asValue = asKlassSvyzNizArmDef
      Case "Норма верхней усиливающей"
        asValue = asUsGOSTVerhArmDef
      Case "Норма нижней усиливающей"
        asValue = asUsGOSTNizArmDef
      Case "Норма нижней"
        asValue = asGOSTNizArmDef
      Case "Норма верхней"
        asValue = asGOSTVerhArmDef
      Case "Норма поперечной"
        asValue = asGOSTPopArmDef
      Case "Норма верхней связевой"
        asValue = asGOSTSvyzVerhArmDef
      Case "Норма нижней связевой"
        asValue = asGOSTSvyzNizArmDef
      Case Else
        MsgBox "Имя параметра простр каркаса не определен!"
        Exit Function
    End Select
  Else
    'для плоских
    Select Case sKey
      Case "Класс верхней связевой арматуры"
          asValue = asKlassVerhSvyzPlosDef
      Case "Класс нижней связевой арматуры"
          asValue = asKlassNizSvyzPlosDef
      Case "ГОСТ верхней связевой арматуры"
          asValue = asGOSTVerhSvyzPlosDef
      Case "ГОСТ нижней связевой арматуры"
          asValue = asGOSTNizSvyzPlosDef
    End Select
  End If
  
  For i = 0 To UBound(asValue)
    GetStringArrayStrDef = GetStringArrayStrDef & asValue(i) & ";"
  Next
'  'убираем последний ";"
'  GetStringArrayStrDef = Left(GetStringArrayStrDef, Len(GetStringArrayStrDef) - 1)
  
End Function

Private Function GetArrayStringDef(sValue As String, sKey As String, bolProsOrPlosKar As Boolean)
  'преобразование строки значений параметра из ини для номеров сечений в массив значений
  
  Dim asValue() As String
  Dim intLenStr As Integer
  Dim intDec As Integer
  Dim intUbound As Integer
  Dim i As Integer
  Dim sDefault As String
  
  If bolProsOrPlosKar = True Then
    Select Case sKey
      Case "Класс верхней усиливающей"
        sDefault = "A-III"
      Case "Класс нижней усиливающей"
        sDefault = "A-III"
      Case "Класс верхней"
        sDefault = "A-III"
      Case "Класс нижней"
        sDefault = "A-III"
      Case "Класс поперечной"
        sDefault = "A-III"
      Case "Класс верхней связевой"
        sDefault = "A-III"
      Case "Класс нижней связевой"
        sDefault = "A-III"
      Case "Норма верхней усиливающей"
        sDefault = "ГОСТ 5781-82"
      Case "Норма нижней усиливающей"
        sDefault = "ГОСТ 5781-82"
      Case "Норма нижней"
        sDefault = "ГОСТ 5781-82"
      Case "Норма верхней"
        sDefault = "ГОСТ 5781-82"
      Case "Норма поперечной"
        sDefault = "ГОСТ 5781-82"
      Case "Норма верхней связевой"
        sDefault = "ГОСТ 5781-82"
      Case "Норма нижней связевой"
        sDefault = "ГОСТ 5781-82"
      Case Else
        MsgBox "Имя параметра простр каркаса не определен!"
        Exit Function
    End Select
    intUbound = UBound(asNSechDef)
  Else
    'для плоских
    Select Case sKey
      Case "Класс верхней связевой арматуры"
          sDefault = "A-III"
      Case "Класс нижней связевой арматуры"
          sDefault = "A-III"
      Case "ГОСТ верхней связевой арматуры"
          sDefault = "ГОСТ 5781-82"
      Case "ГОСТ нижней связевой арматуры"
          sDefault = "ГОСТ 5781-82"
    End Select
    intUbound = UBound(asNSechPlosDef)
  End If
  
  ReDim asValue(intUbound)
  
  If sValue = "" Then
    For i = 0 To intUbound
      asValue(i) = sDefault
    Next
    GoTo ExitHere
  End If
  
  intDec = InStr(sValue, ";")
  If intDec = 0 Then
    asValue(0) = sValue
    For i = 1 To intUbound
      asValue(i) = sDefault
    Next
    GoTo ExitHere
  End If
  intLenStr = Len(sValue)
  Do
    asValue(i) = Left(sValue, intDec - 1)
    intLenStr = intLenStr - intDec
    sValue = Right(sValue, intLenStr)
    intDec = InStr(sValue, ";")
    i = i + 1
  Loop Until intDec = 0
  
  For i = 0 To intUbound
    If asValue(i) = "" Then asValue(i) = sDefault
  Next
  
ExitHere:
  If bolProsOrPlosKar = True Then
    Select Case sKey
      Case "Класс верхней усиливающей"
        asUsKlassVerhArmDef = asValue
      Case "Класс нижней усиливающей"
        asUsKlassNizArmDef = asValue
      Case "Класс верхней"
        asKlassVerhArmDef = asValue
      Case "Класс нижней"
        asKlassNizArmDef = asValue
      Case "Класс поперечной"
        asKlassPopArmDef = asValue
      Case "Класс верхней связевой"
        asKlassSvyzVerhArmDef = asValue
      Case "Класс нижней связевой"
        asKlassSvyzNizArmDef = asValue
      Case "Норма верхней усиливающей"
        asUsGOSTVerhArmDef = asValue
      Case "Норма нижней усиливающей"
        asUsGOSTNizArmDef = asValue
      Case "Норма нижней"
        asGOSTNizArmDef = asValue
      Case "Норма верхней"
        asGOSTVerhArmDef = asValue
      Case "Норма поперечной"
        asGOSTPopArmDef = asValue
      Case "Норма верхней связевой"
        asGOSTSvyzVerhArmDef = asValue
      Case "Норма нижней связевой"
        asGOSTSvyzNizArmDef = asValue
    End Select
  Else
    'для плоских
    Select Case sKey
      Case "Класс верхней связевой арматуры"
          asKlassVerhSvyzPlosDef = asValue
      Case "Класс нижней связевой арматуры"
          asKlassNizSvyzPlosDef = asValue
      Case "ГОСТ верхней связевой арматуры"
          asGOSTVerhSvyzPlosDef = asValue
      Case "ГОСТ нижней связевой арматуры"
          asGOSTNizSvyzPlosDef = asValue
    End Select
  End If
End Function

Private Function GetArrayHvosty(sValue As String, bKirp As Boolean)
  'преобразование строки хвоствов из ини в массив длин хвостов
  Dim intLenStr As Integer
  Dim intDec As Integer
  Dim i As Integer
  Dim iItemLenHvosta As Integer
  
  If sValue = "" Then
DefVal:
    'значения по умолчанию
    If bKirp = False Then
      aiLenHvost(0) = 600
      aiLenHvost(1) = 400
      aiLenHvost(2) = 450
      aiLenHvost(3) = 500
      aiLenHvost(4) = 550
      aiLenHvost(5) = 700
      aiLenHvost(6) = 800
      aiLenHvost(7) = 900
      aiLenHvost(8) = 0
      aiLenHvost(9) = 0
    Else
      aiLenHvostK(0) = 0
      aiLenHvostK(1) = 500
      aiLenHvostK(2) = 600
      aiLenHvostK(3) = 650
      aiLenHvostK(4) = 750
      aiLenHvostK(5) = 800
      aiLenHvostK(6) = 900
      aiLenHvostK(7) = 1000
      aiLenHvostK(8) = 0
      aiLenHvostK(9) = 0
    End If
    
    Exit Function
  End If
  
  intDec = InStr(sValue, ";")
  If intDec = 0 Then
    GoTo DefVal:
  End If
  intLenStr = Len(sValue)
  Do
    iItemLenHvosta = Val(Left(sValue, intDec - 1))
    If bKirp = False Then
      aiLenHvost(i) = iItemLenHvosta
    Else
      aiLenHvostK(i) = iItemLenHvosta
    End If
    intLenStr = intLenStr - intDec
    sValue = Right(sValue, intLenStr)
    intDec = InStr(sValue, ";")
    i = i + 1
  Loop Until intDec = 0
  
End Function

Private Function GetStringHvosty(bKirp As Boolean) As String
  Dim intLenStr As Integer
  Dim intDec As Integer
  Dim i As Integer
  
  For i = 0 To 9
    
    If bKirp = False Then
      GetStringHvosty = GetStringHvosty & aiLenHvost(i) & ";"
    Else
      GetStringHvosty = GetStringHvosty & aiLenHvostK(i) & ";"
    End If
    
  Next
  
'  'убираем последний ;
'  GetStringHvosty = Left(GetStringHvosty, Len(GetStringHvosty) - 1)
  
End Function

'Private Function GetDiamStandard(Diam As Integer) As Integer
'   'проверка соответствия входного диаметра списку стандартных диаметров арматуры
'
'   Select Case Diam
'      Case 6
'         ReturnDiamStandard = Diam
'      Case 8
'         ReturnDiamStandard = Diam
'      Case 10
'         ReturnDiamStandard = Diam
'      Case 12
'         ReturnDiamStandard = Diam
'      Case 14
'         ReturnDiamStandard = Diam
'      Case 16
'         ReturnDiamStandard = Diam
'      Case 18
'         ReturnDiamStandard = Diam
'      Case 20
'         ReturnDiamStandard = Diam
'      Case 22
'         ReturnDiamStandard = Diam
'      Case 25
'         ReturnDiamStandard = Diam
'      Case 28
'         ReturnDiamStandard = Diam
'      Case 32
'         ReturnDiamStandard = Diam
'      Case 36
'         ReturnDiamStandard = Diam
'      Case 40
'         ReturnDiamStandard = Diam
'      Case Else
'         ReturnDiamStandard = 8
'   End Select
'
'End Function

Private Sub Class_Terminate()
'  'сохранение настроек в ини
'  SaveOptionsToIni
End Sub

Public Sub SaveOptions()
  'сохранение настроек из вкладки Настройки
  
  'слой для каркасов
  psKarLayer = FormSpecRost.TextBoxLayerKarDef
  'слой для сеток
  psSetkyLayer = FormSpecRost.TextBoxLayerSetkyDef
  'слой для доп.стержней
  psDopSterLayer = FormSpecRost.TextBoxLayerDopSterDef
  'имя для сеток
  psSetkaConst = FormSpecRost.TextBoxSetkyBlName
  'имя для доп.стержней
  psDopSterConst = FormSpecRost.TextBoxDopSterBlName
  'радиус наложения
  pintRadNalog = FormSpecRost.TextBoxRadNalog
  'шаг доп.поп.стержня
  piShagDopPopSterDef = FormSpecRost.TextBoxShagDopPopSterDef
  'диаметры поумолчанию для каркасов
  piDiamKarVerhDef = FormSpecRost.TextBoxDiamVerhArmDef
  piDiamKarNizDef = FormSpecRost.TextBoxDiamNizArmDef
  piDiamKarPopDef = FormSpecRost.TextBoxDiamPopArmDef
  'хвосты
  aiLenHvost(0) = FormSpecRost.TextBoxHvost0
  aiLenHvost(1) = FormSpecRost.TextBoxHvost1
  aiLenHvost(2) = FormSpecRost.TextBoxHvost2
  aiLenHvost(3) = FormSpecRost.TextBoxHvost3
  aiLenHvost(4) = FormSpecRost.TextBoxHvost4
  aiLenHvost(5) = FormSpecRost.TextBoxHvost5
  aiLenHvost(6) = FormSpecRost.TextBoxHvost6
  aiLenHvost(7) = FormSpecRost.TextBoxHvost7
  aiLenHvost(8) = FormSpecRost.TextBoxHvost8
  aiLenHvost(9) = FormSpecRost.TextBoxHvost9
  'хвосты для Кирпички
  aiLenHvostK(0) = FormSpecRost.TextBoxHvost0K
  aiLenHvostK(1) = FormSpecRost.TextBoxHvost1K
  aiLenHvostK(2) = FormSpecRost.TextBoxHvost2K
  aiLenHvostK(3) = FormSpecRost.TextBoxHvost3K
  aiLenHvostK(4) = FormSpecRost.TextBoxHvost4K
  aiLenHvostK(5) = FormSpecRost.TextBoxHvost5K
  aiLenHvostK(6) = FormSpecRost.TextBoxHvost6K
  aiLenHvostK(7) = FormSpecRost.TextBoxHvost7K
  aiLenHvostK(8) = FormSpecRost.TextBoxHvost8K
  aiLenHvostK(9) = FormSpecRost.TextBoxHvost9K
  
  'классы арматуры
  psKlassVerhDef = FormSpecRost.TextBoxKlassVerhDef
  psKlassNizDef = FormSpecRost.TextBoxKlassNizDef
  psKlassPopDef = FormSpecRost.TextBoxKlassPopDef
  psKlassSvyzVerhDef = FormSpecRost.TextBoxKlassSvyzVerhDef
  psKlassSvyzNizDef = FormSpecRost.TextBoxKlassSvyzNizDef
  psKlassSetokDef = FormSpecRost.TextBoxKlassSetokDef
  psKlassDopStergDef = FormSpecRost.TextBoxKlassDopStergDef
  psKlassShpilekDef = FormSpecRost.TextBoxKlassShpilekDef
  psGOSTVerhDef = FormSpecRost.TextBoxGOSTVerhDef
  psGOSTNizDef = FormSpecRost.TextBoxGOSTNizDef
  psGOSTPopDef = FormSpecRost.TextBoxGOSTPopDef
  psGOSTSvyzVerhDef = FormSpecRost.TextBoxGOSTSvyzVerhDef
  psGOSTSvyzNizDef = FormSpecRost.TextBoxGOSTSvyzNizDef
  psGOSTSetokDef = FormSpecRost.TextBoxGOSTSetokDef
  psGOSTDopStergDef = FormSpecRost.TextBoxGOSTDopStergDef
  psGOSTShpilekDef = FormSpecRost.TextBoxGOSTShpilekDef
  'Для расчета длины связ стержней (Шир сеч - b)
  piLenSvyzB = FormSpecRost.TextBoxLenSvyzB
    'для Кирпички
    piLenSvyzBK = FormSpecRost.TextBoxLenSvyzBK
  'TagString МаркиК
  psMarkaKTag = FormSpecRost.TextBoxMarkaKTag
  'галочка расчета по кирпичке
  pbMarkaKValue = FormSpecRost.CheckBoxMarkaK.Value
  
End Sub

Private Function GetStringNSechDef() As String
  
  Dim i As Integer
  
  For i = 0 To UBound(asNSechDef)
    GetStringNSechDef = GetStringNSechDef & asNSechDef(i) & ";"
  Next
  'убираем последний ;
'  GetStringNSechDef = Left(GetStringNSechDef, Len(GetStringNSechDef) - 1)
  
End Function
Private Function GetStringNSechPlosDef() As String
  
  Dim i As Integer
  
  For i = 0 To UBound(asNSechPlosDef)
    GetStringNSechPlosDef = GetStringNSechPlosDef & asNSechPlosDef(i) & ";"
  Next
  
End Function

Public Function GetLenHvosta(intNumbr As Integer) As Integer
  
  If intNumbr > 9 Then Exit Function
    
  Dim bKirp As Boolean
  Dim vaHvosty As Variant
  
  bKirp = FormSpecRost.CheckBoxMarkaK.Value
  
  If bKirp = False Then
    GetLenHvosta = aiLenHvost(intNumbr)
  Else
    GetLenHvosta = aiLenHvostK(intNumbr)
  End If
End Function

Private Function GetStringArrayBolUs() As String
  'возвращает строку признаков битов
  Dim i As Integer
  
  For i = 0 To UBound(abolUsilenie)
    If abolUsilenie(i) = True Then
      GetStringArrayBolUs = GetStringArrayBolUs & "1" & ";"
    Else
      GetStringArrayBolUs = GetStringArrayBolUs & "0" & ";"
    End If
  Next
End Function

Private Function GetArrayBolUs(sValue As String)
  'преобразовывает строку битов в массив abolUsilenie
  'сохраняется в массив abolUsilenie()
  Dim i As Integer
  Dim intDec As Integer
  Dim intLenStr As Integer
  Dim intUbound As Integer
  
  intUbound = UBound(asNSechDef)
  
  ReDim abolUsilenie(intUbound)
  
  If sValue = "" Then
    'все значения будут false
    Exit Function
  End If
  
  intDec = InStr(sValue, ";")
  If intDec = 0 Then
    Exit Function
  End If
  
  intLenStr = Len(sValue)
  Do
    If Val(sValue) = 1 Then
      abolUsilenie(i) = True
    Else
      abolUsilenie(i) = False
    End If
    intLenStr = intLenStr - intDec
    sValue = Right(sValue, intLenStr)
    intDec = InStr(sValue, ";")
    i = i + 1
  Loop Until intDec = 0
  
End Function


''Сохранение записей о расчетах из комбобокса расчетов
'Private Function SaveRaschetyToIni()
'
'  Dim i As Integer
'  Dim sValue As String
'  Dim comboBoxRaschet As ComboBox
'
'  Set comboBoxRaschet = FormSpecRost.ComboBoxLoadRaschet
'
'  If comboBoxRaschet.ListCount = 0 Then Exit Function
'
'  'Записиваем все расчеты из комбобокса в ини по порядку
'  For i = 0 To comboBoxRaschet.ListCount - 1
'    sValue = comboBoxRaschet.List(i, 3) & ";" & comboBoxRaschet.List(i, 1) & ";" & comboBoxRaschet.List(i, 2) ' [Дата];[Имя файла ростверка];[Путь к файлу расчетов]
'    oIni.WriteFile scSectionForSavedRaschet, CStr(i), sValue
'  Next
'
'End Function

'Сохранение записей о расчетах из комбобокса расчетов в ини
'Private Function LoadRaschetyFromIni()
'
'  Dim i As Integer
'  Dim intDec As Integer
'  Dim sValue As String
'  Dim sData As String
'  Dim sFileRost As String
'  Dim sFullPathRaschet As String
'  Dim comboBoxRaschet As ComboBox
'  Dim dataRaschet As Date
'
'  Set comboBoxRaschet = FormSpecRost.ComboBoxLoadRaschet
'
'  'Записиваем все расчеты из ини в комбобокса по порядку
'  While True
'
'    sValue = oIni.GetFile(scSectionForSavedRaschet, CStr(i))
'    If sValue = "" Then Exit Function
'
'    'MsgBox sValue
'
'    intDec = InStr(sValue, ";")
'    sData = Left(sValue, intDec - 1)
'    dataRaschet = sData
'
'    sValue = Mid(sValue, intDec + 1)
'    intDec = InStr(sValue, ";")
'    sFileRost = Left(sValue, intDec - 1)
'
'    sValue = Mid(sValue, intDec + 1)
'    sFullPathRaschet = sValue
'
'    comboBoxRaschet.AddItem sFileRost & " : " & dataRaschet, i
'    comboBoxRaschet.List(i, 1) = sFileRost
'    comboBoxRaschet.List(i, 2) = sFullPathRaschet
'    comboBoxRaschet.List(i, 3) = dataRaschet
'
'    i = i + 1
'  Wend
'
'End Function

Public Function ClearProsKarParamSech()
  
    Erase asNSechDef
    Erase aiLenSechDef
    Erase aiHeightRostDef
    Erase aiShagSvyzNizArmDef
    Erase aiShagSvyzVerhArmDef
    Erase aiDiamSvyzNizArmDef
    Erase aiDiamSvyzVerhArmDef
    Erase aiZachBetNizDef
    Erase aiZachBetVerhDef
    Erase abolUsilenie
    Erase aiUsLenSechDef
    Erase aiUsDiamNizArmDef
    Erase aiUsDiamVerhArmDef
    Erase aiUsShagVerhArmDef
    Erase aiUsShagNizArmDef
    Erase asUsKlassNizArmDef
    Erase asUsKlassVerhArmDef
    Erase asUsGOSTNizArmDef
    Erase asUsGOSTVerhArmDef
    Erase asKlassVerhArmDef
    Erase asKlassNizArmDef
    Erase asKlassPopArmDef
    Erase asKlassSvyzNizArmDef
    Erase asKlassSvyzVerhArmDef
    Erase asGOSTNizArmDef
    Erase asGOSTVerhArmDef
    Erase asGOSTPopArmDef
    Erase asGOSTSvyzNizArmDef
    Erase asGOSTSvyzVerhArmDef
    
    ReDim asNSechDef(0)
    ReDim aiLenSechDef(0)
    ReDim aiHeightRostDef(0)
    ReDim aiShagSvyzNizArmDef(0)
    ReDim aiShagSvyzVerhArmDef(0)
    ReDim aiDiamSvyzNizArmDef(0)
    ReDim aiDiamSvyzVerhArmDef(0)
    ReDim aiZachBetNizDef(0)
    ReDim aiZachBetVerhDef(0)
    ReDim abolUsilenie(0)
    ReDim aiUsLenSechDef(0)
    ReDim aiUsDiamNizArmDef(0)
    ReDim aiUsDiamVerhArmDef(0)
    ReDim aiUsShagVerhArmDef(0)
    ReDim aiUsShagNizArmDef(0)
    ReDim asUsKlassNizArmDef(0)
    ReDim asUsKlassVerhArmDef(0)
    ReDim asUsGOSTNizArmDef(0)
    ReDim asUsGOSTVerhArmDef(0)
    ReDim asKlassVerhArmDef(0)
    ReDim asKlassNizArmDef(0)
    ReDim asKlassPopArmDef(0)
    ReDim asKlassSvyzNizArmDef(0)
    ReDim asKlassSvyzVerhArmDef(0)
    ReDim asGOSTNizArmDef(0)
    ReDim asGOSTVerhArmDef(0)
    ReDim asGOSTPopArmDef(0)
    ReDim asGOSTSvyzNizArmDef(0)
    ReDim asGOSTSvyzVerhArmDef(0)
  
End Function


Public Function LoadPlosKarParamProsSechDef()
  'установка значений параметров простр.каркаса для плоских каркасов из значения По-умолчанию
  
  Dim i As Integer
  Dim bol0Sech As Boolean
    
  For i = 0 To UBound(asNSechDef)
    If asNSechDef(i) = "0" Then
      bol0Sech = True
      Exit For
    End If
  Next
  If bol0Sech = True Then
    'считываем значения по-умолчанию с настроек
    'заполняем поля
    'высота ростверка
    'если высота ростверка не задана в имени каркаса (в скобках - "(6)")
    If FormSpecRost.TextBoxHeightRost.Enabled = True Then
      FormSpecRost.TextBoxHPlosKar = aiHeightRostDef(i)
    End If
    FormSpecRost.TextBoxZachNizPlosKar = aiZachBetNizDef(i)
    FormSpecRost.TextBoxZachVerhPlosKar = aiZachBetVerhDef(i)
    FormSpecRost.TextBoxKlassVerhPlosKar = asKlassVerhArmDef(i)
    FormSpecRost.TextBoxKlassNizPlosKar = asKlassNizArmDef(i)
    FormSpecRost.TextBoxKlassPopPlosKar = asKlassPopArmDef(i)
    FormSpecRost.TextBoxGOSTNizPlosKar = asGOSTNizArmDef(i)
    FormSpecRost.TextBoxGOSTVerhPlosKar = asGOSTVerhArmDef(i)
    FormSpecRost.TextBoxGOSTPopPlosKar = asGOSTPopArmDef(i)
  End If
    
End Function

Public Function SaveForShtamp()
  'pfgbcm настроек из вкладки Исходные данные
  
  'Шифр
  pForShtampShifr = FormSpecRost.TextBoxShifr
  pForShtampBS = FormSpecRost.CheckBoxShifrBS.Value
  pForShtampNPart = FormSpecRost.TextBoxNpart
  pForShtampAdres = FormSpecRost.TextBoxAdres
  pForShtampNaimenObject = FormSpecRost.TextBoxNaimenDoma
  pForShtampPost1 = FormSpecRost.TextBoxPost1
  pForShtampPost2 = FormSpecRost.TextBoxPost2
  pForShtampPost3 = FormSpecRost.TextBoxPost3
  pForShtampPost4 = FormSpecRost.TextBoxPost4
  pForShtampPost5 = FormSpecRost.TextBoxPost5
  pForShtampPost6 = FormSpecRost.TextBoxPost6
  pForShtampFam1 = FormSpecRost.TextBoxFam1
  pForShtampFam2 = FormSpecRost.TextBoxFam2
  pForShtampFam3 = FormSpecRost.TextBoxFam3
  pForShtampFam4 = FormSpecRost.TextBoxFam4
  pForShtampFam5 = FormSpecRost.TextBoxFam5
  pForShtampFam6 = FormSpecRost.TextBoxFam6
  pForSgtampChkBox1ForTitulPost = FormSpecRost.cbShtampTitul1
  pForSgtampChkBox2ForTitulPost = FormSpecRost.cbShtampTitul2
  pForSgtampChkBox3ForTitulPost = FormSpecRost.cbShtampTitul3
  pForSgtampChkBox1ForShtamp = FormSpecRost.cbShtamp1
  pForSgtampChkBox2ForShtamp = FormSpecRost.cbShtamp2
  pForSgtampChkBox3ForShtamp = FormSpecRost.cbShtamp3
  pForSgtampChkBox4ForShtamp = FormSpecRost.cbShtamp4
  pForSgtampChkBox5ForShtamp = FormSpecRost.cbShtamp5
  pForSgtampChkBox6ForShtamp = FormSpecRost.cbShtamp6

End Function

Attribute VB_Name = "clPlosKarSech"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'параметры сечений плоского каркаса
Public sMarkaPlosKar As String
'параметры сечения плоского каркаса
Dim asNSech() As String
Dim aiLenSech() As Integer
Dim aiKolSech() As Integer 'кол-во сечений на чертеже
Dim aiKolKarInSech() As Integer 'кол-во каркасов в сечении
Dim aiShagVerh() As Integer
Dim aiDiamVerh() As Integer
Dim asKlassVerh() As String
Dim asGOSTVerh() As String
Dim aiShagNiz() As Integer
Dim aiDiamNiz() As Integer
Dim asKlassNiz() As String
Dim asGOSTNiz() As String

'параметры плоского каркаса
Public piKolShtuk As Integer
Public piKolBl As Integer
Public piKolKar As Integer
Public piLenRab As Integer

Public iCountSech As Integer 'кол-во типо сечений

'Изменения 07,04,10 !!!!!!!!????????
Public poPlosKar As clKarkas

Public Sub SetParamSech(iLenKarRab As Integer)
  'сохранить параметры сечений с формы FormSpecRost.ListViewPlosKarSech
  
  Dim oListItem As ListItem
  Dim iUbound As Integer
  Dim i As Integer
  
  piLenRab = iLenKarRab
  
  iCountSech = FormSpecRost.ListViewPlosKarSech.ListItems.Count
  iUbound = iCountSech - 1
  'переопределяем массивы
  ReDim asNSech(iUbound)
  ReDim aiLenSech(iUbound)
  ReDim aiKolSech(iUbound)
  ReDim aiKolKarInSech(iUbound)
  ReDim aiShagVerh(iUbound)
  ReDim aiDiamVerh(iUbound)
  ReDim asKlassVerh(iUbound)
  ReDim asGOSTVerh(iUbound)
  ReDim aiShagNiz(iUbound)
  ReDim aiDiamNiz(iUbound)
  ReDim asKlassNiz(iUbound)
  ReDim asGOSTNiz(iUbound)
  
  For i = 0 To iUbound
    Set oListItem = FormSpecRost.ListViewPlosKarSech.ListItems(i + 1)
    
    asNSech(i) = oListItem.Text
    aiLenSech(i) = oListItem.ListSubItems(1)
    aiKolSech(i) = oListItem.ListSubItems(2)
    aiKolKarInSech(i) = oListItem.ListSubItems(3)
    aiShagVerh(i) = oListItem.ListSubItems(4)
    aiDiamVerh(i) = oListItem.ListSubItems(5)
    asKlassVerh(i) = oListItem.ListSubItems(6)
    asGOSTVerh(i) = oListItem.ListSubItems(7)
    aiShagNiz(i) = oListItem.ListSubItems(8)
    aiDiamNiz(i) = oListItem.ListSubItems(9)
    asKlassNiz(i) = oListItem.ListSubItems(10)
    asGOSTNiz(i) = oListItem.ListSubItems(11)
  Next
  
End Sub

Public Sub GetParamSech()
  'заполнить параметры сечений в формУ FormSpecRost.ListViewPlosKarSech
  
  Dim oListItem As ListItem
  Dim i As Integer
  
  FormSpecRost.ListViewPlosKarSech.ListItems.Clear
  If iCountSech = 0 Then Exit Sub
  
  'заполняем листвиевер сечений
  For i = 0 To iCountSech - 1
    Set oListItem = FormSpecRost.ListViewPlosKarSech.ListItems.Add(, , asNSech(i))
    
    oListItem.SubItems(1) = aiLenSech(i)
    oListItem.SubItems(2) = aiKolSech(i)
    oListItem.SubItems(3) = aiKolKarInSech(i)
    oListItem.SubItems(4) = aiShagVerh(i)
    oListItem.SubItems(5) = aiDiamVerh(i)
    oListItem.SubItems(6) = asKlassVerh(i)
    oListItem.SubItems(7) = asGOSTVerh(i)
    oListItem.SubItems(8) = aiShagNiz(i)
    oListItem.SubItems(9) = aiDiamNiz(i)
    oListItem.SubItems(10) = asKlassNiz(i)
    oListItem.SubItems(11) = asGOSTNiz(i)
    
  Next
  
  'выделяем первый
  FormSpecRost.ListViewPlosKarSech.ListItems.Item(1).Selected = True
  FormSpecRost.ListViewPlosKarSech_ItemClick FormSpecRost.ListViewPlosKarSech.ListItems.Item(1)
  
End Sub

'Public Property Get CountSech() As Integer
'  CountSech = iCountSech
'End Property
'Public Property Let CountSech(ByVal vNewValue As Integer)
'  iCountSech = vNewValue
'  'переопределяем массивы
'  ReDim asNSech(iCountSech)
'  ReDim aiLenSech(iCountSech)
'  ReDim aiKolSech(iCountSech)
'  ReDim aiKolKarInSech(iCountSech)
'  ReDim aiShagVerh(iCountSech)
'  ReDim aiDiamVerh(iCountSech)
'  ReDim asKlassVerh(iCountSech)
'  ReDim asGOSTVerh(iCountSech)
'  ReDim aiShagNiz(iCountSech)
'  ReDim aiDiamNiz(iCountSech)
'  ReDim asKlassNiz(iCountSech)
'  ReDim asGOSTNiz(iCountSech)
'End Property

Public Function ProvKolSech() As Boolean
  'проверка кол-во кар в сечениях = кол-ву каркасов
  
  Dim i As Integer
  Dim iKolKar As Integer
  Dim iKolKarPoSech As Integer 'кол каркасов по параметрам сечений
    
  'определяем общее кол-во каркасов во всех сечениях
  For i = 0 To iCountSech - 1
    iKolKarPoSech = iKolKarPoSech + aiKolSech(i) * aiKolKarInSech(i)
  Next
  
  If piKolKar = 0 Then
    iKolKar = poPlosKar.intKolKar
  Else
    iKolKar = piKolKar
  End If
  
  If iKolKar = iKolKarPoSech Then
    ProvKolSech = True
  End If
  
End Function

Public Function GetColDopSter() As Collection
  'массив доп.стержней всех сечений каркаса
  
  Dim oDopSter As clDopStergen
  Dim oDopSterTemp As clDopStergen
  Dim iValue As Integer
  Dim iZazor As Integer
  Dim i As Integer
  
  On Error Resume Next
  
  Set GetColDopSter = New Collection
  
  If FormSpecRost.CheckBoxMarkaK.Value = False Then
    iZazor = pclOptions.piLenSvyzB
  Else
    iZazor = pclOptions.piLenSvyzBK
  End If
  
  For i = 0 To iCountSech - 1
    If aiLenSech(i) <> 0 Then
      'верхние соедиительные стержни
      Set oDopSter = New clDopStergen
      oDopSter.iDiametr = aiDiamVerh(i)
      oDopSter.iLenght = aiLenSech(i) - iZazor
      'кол-во стержней
      oDopSter.iKolvo = piLenRab \ aiShagVerh(i) + 1    'деление нацело
      iValue = piLenRab Mod aiShagVerh(i)
      If iValue > 25 Then oDopSter.iKolvo = oDopSter.iKolvo + 1
      oDopSter.iKolvo = oDopSter.iKolvo * aiKolSech(i)
      oDopSter.sKlassArm = asKlassVerh(i)
      oDopSter.sGOSTArm = asGOSTVerh(i)
      oDopSter.ObrabNaimenov
      'добавляем стержень в коллекцию
      Set oDopSterTemp = GetColDopSter.Item(oDopSter.sNaimenovanie)
      If Err Then
        'нет такого, добавляем
        Err.Clear
        GetColDopSter.Add oDopSter, oDopSter.sNaimenovanie
      Else
        'добавляем кол-во
        oDopSterTemp.iKolvo = oDopSterTemp.iKolvo + oDopSter.iKolvo
      End If
      
      'нижние соед стержни
      Set oDopSter = New clDopStergen
      oDopSter.iDiametr = aiDiamNiz(i)
      oDopSter.iLenght = aiLenSech(i) - iZazor
      'кол-во стержней
      oDopSter.iKolvo = piLenRab \ aiShagNiz(i) + 1    'деление нацело
      iValue = piLenRab Mod aiShagNiz(i)
      If iValue > 25 Then oDopSter.iKolvo = oDopSter.iKolvo + 1
      oDopSter.iKolvo = oDopSter.iKolvo * aiKolSech(i)
      oDopSter.sKlassArm = asKlassNiz(i)
      oDopSter.sGOSTArm = asGOSTNiz(i)
      oDopSter.ObrabNaimenov
      'добавляем стержень в коллекцию
      Set oDopSterTemp = GetColDopSter.Item(oDopSter.sNaimenovanie)
      If Err Then
        'нет такого, добавляем
        Err.Clear
        GetColDopSter.Add oDopSter, oDopSter.sNaimenovanie
      Else
        'добавляем кол-во
        oDopSterTemp.iKolvo = oDopSterTemp.iKolvo + oDopSter.iKolvo
      End If
    End If 'If aiLenSech(i) <> 0 Then
  Next
  
  On Error GoTo 0
  
End Function

Public Function GetStringPlosKarSechToTxt() As String
  'возвращает строку параметров плоского сечения для записи в txt
  
  Dim i As Integer
  
  For i = 0 To iCountSech - 1
    GetStringPlosKarSechToTxt = GetStringPlosKarSechToTxt & sMarkaPlosKar & ";" & asNSech(i) & ";" & aiLenSech(i) & ";" & aiKolSech(i) & ";" & aiKolKarInSech(i) & ";" & aiShagVerh(i) _
      & ";" & aiDiamVerh(i) & ";" & asKlassVerh(i) & ";" & asGOSTVerh(i) & ";" & aiShagNiz(i) & ";" & aiDiamNiz(i) & ";" & asKlassNiz(i) & ";" & asGOSTNiz(i) & ";"
  Next
  
End Function

Public Function GetPlosKarSechFromTXTString(sTxtString As String)
  'заполнение параметров сечения из строки файла данных txt
  
  Dim iDec As Integer
  Dim sval As String
  Dim iCount As Integer
  
  If sTxtString = "" Then Exit Function
  
  iDec = InStr(sTxtString, ";")
  If iDec = 0 Then Exit Function
  
  Do While iDec <> 0
    ReDim Preserve asNSech(iCount)
    ReDim Preserve aiLenSech(iCount)
    ReDim Preserve aiKolSech(iCount)
    ReDim Preserve aiKolKarInSech(iCount)
    ReDim Preserve aiShagVerh(iCount)
    ReDim Preserve aiDiamVerh(iCount)
    ReDim Preserve asKlassVerh(iCount)
    ReDim Preserve asGOSTVerh(iCount)
    ReDim Preserve aiShagNiz(iCount)
    ReDim Preserve aiDiamNiz(iCount)
    ReDim Preserve asKlassNiz(iCount)
    ReDim Preserve asGOSTNiz(iCount)
    
    'имя плос кар
    sMarkaPlosKar = Left(sTxtString, iDec - 1)
    sTxtString = Mid(sTxtString, iDec + 1)
    iDec = InStr(sTxtString, ";")
    If iDec = 0 Then Exit Do
    'номер сечения
    asNSech(iCount) = Left(sTxtString, iDec - 1)
    sTxtString = Mid(sTxtString, iDec + 1)
    iDec = InStr(sTxtString, ";")
    If iDec = 0 Then Exit Do
    'ширина сечения
    aiLenSech(iCount) = Val(Left(sTxtString, iDec - 1))
    sTxtString = Mid(sTxtString, iDec + 1)
    iDec = InStr(sTxtString, ";")
    If iDec = 0 Then Exit Do
    'кол-во сечений
    aiKolSech(iCount) = Val(Left(sTxtString, iDec - 1))
    sTxtString = Mid(sTxtString, iDec + 1)
    iDec = InStr(sTxtString, ";")
    If iDec = 0 Then Exit Do
    'кол-во кар в сечений
    aiKolKarInSech(iCount) = Val(Left(sTxtString, iDec - 1))
    sTxtString = Mid(sTxtString, iDec + 1)
    iDec = InStr(sTxtString, ";")
    If iDec = 0 Then Exit Do
    'шаг верхних
    aiShagVerh(iCount) = Val(Left(sTxtString, iDec - 1))
    sTxtString = Mid(sTxtString, iDec + 1)
    iDec = InStr(sTxtString, ";")
    If iDec = 0 Then Exit Do
    'диам верхних
    aiDiamVerh(iCount) = Val(Left(sTxtString, iDec - 1))
    sTxtString = Mid(sTxtString, iDec + 1)
    iDec = InStr(sTxtString, ";")
    If iDec = 0 Then Exit Do
    'класс верхних
    asKlassVerh(iCount) = Left(sTxtString, iDec - 1)
    sTxtString = Mid(sTxtString, iDec + 1)
    iDec = InStr(sTxtString, ";")
    If iDec = 0 Then Exit Do
    'гост верхних
    asGOSTVerh(iCount) = Left(sTxtString, iDec - 1)
    sTxtString = Mid(sTxtString, iDec + 1)
    iDec = InStr(sTxtString, ";")
    If iDec = 0 Then Exit Do
    'шаг нижних
    aiShagNiz(iCount) = Val(Left(sTxtString, iDec - 1))
    sTxtString = Mid(sTxtString, iDec + 1)
    iDec = InStr(sTxtString, ";")
    If iDec = 0 Then Exit Do
    'диам нижних
    aiDiamNiz(iCount) = Val(Left(sTxtString, iDec - 1))
    sTxtString = Mid(sTxtString, iDec + 1)
    iDec = InStr(sTxtString, ";")
    If iDec = 0 Then Exit Do
    'класс нижних
    asKlassNiz(iCount) = Left(sTxtString, iDec - 1)
    sTxtString = Mid(sTxtString, iDec + 1)
    iDec = InStr(sTxtString, ";")
    If iDec = 0 Then Exit Do
    'гост нижних
    asGOSTNiz(iCount) = Left(sTxtString, iDec - 1)
    sTxtString = Mid(sTxtString, iDec + 1)
    iDec = InStr(sTxtString, ";")
    If iDec = 0 Then Exit Do
    
    iCount = iCount + 1
  Loop
  
  'кол-во сечений
  iCountSech = iCount + 1
  'имя плос кар
  
End Function

Public Function GetVArray(sType As String) As Variant
  'возвращает Varian массив заданного имени
  
  Select Case sType
    Case "asNSech"
      GetVArray = asNSech
    Case "aiLenSech"
      GetVArray = aiLenSech
    Case "aiKolSech"
      GetVArray = aiKolSech
    Case "aiKolKarInSech"
      GetVArray = aiKolKarInSech
    Case "aiShagVerh"
      GetVArray = aiShagVerh
    Case "aiDiamVerh"
      GetVArray = aiDiamVerh
    Case "asKlassVerh"
      GetVArray = asKlassVerh
    Case "asGOSTVerh"
      GetVArray = asGOSTVerh
    Case "aiShagNiz"
      GetVArray = aiShagNiz
    Case "aiDiamNiz"
      GetVArray = aiDiamNiz
    Case "asKlassNiz"
      GetVArray = asKlassNiz
    Case "asGOSTNiz"
      GetVArray = asGOSTNiz
  End Select
  
End Function

Public Function SetVArray(sType As String, vArray As Variant)
  'возвращает Varian массив заданного имени
  Dim vArrayVal As Variant
  Dim i As Integer
  
  Select Case sType
    Case "asNSech"
      ReDim asNSech(UBound(vArray))
      For i = 0 To UBound(vArray)
        asNSech(i) = vArray(i)
      Next
    Case "aiLenSech"
      ReDim aiLenSech(UBound(vArray))
       For i = 0 To UBound(vArray)
        aiLenSech(i) = vArray(i)
      Next
    Case "aiKolSech"
      ReDim aiKolSech(UBound(vArray))
       For i = 0 To UBound(vArray)
        aiKolSech(i) = vArray(i)
      Next
    Case "aiKolKarInSech"
      ReDim aiKolKarInSech(UBound(vArray))
       For i = 0 To UBound(vArray)
        aiKolKarInSech(i) = vArray(i)
      Next
    Case "aiShagVerh"
      ReDim aiShagVerh(UBound(vArray))
      For i = 0 To UBound(vArray)
        aiShagVerh(i) = vArray(i)
      Next
    Case "aiDiamVerh"
      ReDim aiDiamVerh(UBound(vArray))
       For i = 0 To UBound(vArray)
        aiDiamVerh(i) = vArray(i)
      Next
    Case "asKlassVerh"
      ReDim asKlassVerh(UBound(vArray))
      For i = 0 To UBound(vArray)
        asKlassVerh(i) = vArray(i)
      Next
    Case "asGOSTVerh"
      ReDim asGOSTVerh(UBound(vArray))
      For i = 0 To UBound(vArray)
        asGOSTVerh(i) = vArray(i)
      Next
    Case "aiShagNiz"
      ReDim aiShagNiz(UBound(vArray))
       For i = 0 To UBound(vArray)
        aiShagNiz(i) = vArray(i)
      Next
    Case "aiDiamNiz"
      ReDim aiDiamNiz(UBound(vArray))
       For i = 0 To UBound(vArray)
        aiDiamNiz(i) = vArray(i)
      Next
    Case "asKlassNiz"
      ReDim asKlassNiz(UBound(vArray))
      For i = 0 To UBound(vArray)
        asKlassNiz(i) = vArray(i)
      Next
    Case "asGOSTNiz"
      ReDim asGOSTNiz(UBound(vArray))
      For i = 0 To UBound(vArray)
        asGOSTNiz(i) = vArray(i)
      Next
  End Select
  
End Function

Attribute VB_Name = "clProsKarSech"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'параметры применяемых сечений простр.каркасов в данном расчете

'параметры сечения простр каркаса
Dim asNSech() As String
Dim aiLenSech() As Integer
Dim aiHeightRostv() As Integer
Dim aiShagDopPopSter() As Integer
Dim aiShagSvyzVerh() As Integer
Dim aiShagSvyzNiz() As Integer
Dim aiDiamSvyzVerh() As Integer
Dim aiDiamSvyzNiz() As Integer
Dim aiZachBetVerh() As Integer
Dim aiZachBetNiz() As Integer
Dim asKlassVerh() As String
Dim asKlassNiz() As String
Dim asKlassPop() As String
Dim asKlassSvyzVerh() As String
Dim asKlassSvyzNiz() As String
'параметры усиления
Dim abUsilenie() As Boolean
Dim aiUsLenght() As Integer
Dim aiUsShagVerh() As Integer
Dim aiUsShagNiz() As Integer
Dim aiUsDiamVerh() As Integer
Dim aiUsDiamNiz() As Integer
Dim asUsKlassVerh() As String
Dim asUsKlassNiz() As String
Dim asUsGostVerh() As String
Dim asUsGostNiz() As String

Dim iCountSech As Integer 'кол-во типо сечений

Public Sub SetParamSech()
  'сохранить параметры сечения с формы FormSpecRost
  
  Dim oListItem As ListItem
  Dim iUbound As Integer
  Dim i As Integer
  Dim bolYes As Boolean
  
  'если уже было это сечение
  For i = 0 To iCountSech - 1
    If asNSech(i) = FormSpecRost.TextBoxNSech Then
      iUbound = i
      bolYes = True
      Exit For
    End If
  Next
  If bolYes = False Then
    'добавляем индекс для нового сечсения
    iCountSech = iCountSech + 1
    iUbound = iCountSech - 1
    'переопределяем массивы
    ReDim Preserve asNSech(iUbound)
    ReDim Preserve aiLenSech(iUbound)
    ReDim Preserve aiHeightRostv(iUbound)
    ReDim Preserve aiShagDopPopSter(iUbound)
    ReDim Preserve aiShagSvyzVerh(iUbound)
    ReDim Preserve aiShagSvyzNiz(iUbound)
    ReDim Preserve aiDiamSvyzVerh(iUbound)
    ReDim Preserve aiDiamSvyzNiz(iUbound)
    ReDim Preserve aiZachBetVerh(iUbound)
    ReDim Preserve aiZachBetNiz(iUbound)
    ReDim Preserve asKlassVerh(iUbound)
    ReDim Preserve asKlassNiz(iUbound)
    ReDim Preserve asKlassPop(iUbound)
    ReDim Preserve asKlassSvyzVerh(iUbound)
    ReDim Preserve asKlassSvyzNiz(iUbound)
    ReDim Preserve abUsilenie(iUbound)
    ReDim Preserve aiUsLenght(iUbound)
    ReDim Preserve aiUsShagVerh(iUbound)
    ReDim Preserve aiUsShagNiz(iUbound)
    ReDim Preserve aiUsDiamVerh(iUbound)
    ReDim Preserve aiUsDiamNiz(iUbound)
    ReDim Preserve asUsKlassVerh(iUbound)
    ReDim Preserve asUsKlassNiz(iUbound)
    ReDim Preserve asUsGostVerh(iUbound)
    ReDim Preserve asUsGostNiz(iUbound)
  End If
  
  'сохраняем параметры сечения
  asNSech(iUbound) = FormSpecRost.TextBoxNSech
  aiLenSech(iUbound) = FormSpecRost.TextBoxLenSech
  aiHeightRostv(iUbound) = FormSpecRost.TextBoxHeightRost
 ' aiShagDopPopSter(iUbound) = FormSpecRost.TextBoxShagDopPopSter
  aiShagSvyzVerh(iUbound) = FormSpecRost.TextBoxShagVerhSvyzSter
  aiShagSvyzNiz(iUbound) = FormSpecRost.TextBoxShagNizSvyzSter
  aiDiamSvyzVerh(iUbound) = FormSpecRost.TextBoxDiamVerhSvyzSter
  aiDiamSvyzNiz(iUbound) = FormSpecRost.TextBoxDiamNizSvyzSter
  aiZachBetVerh(iUbound) = FormSpecRost.TextBoxVerhZachBet
  aiZachBetNiz(iUbound) = FormSpecRost.TextBoxNizZachBet
  asKlassVerh(iUbound) = FormSpecRost.TextBoxKlassVerhArm
  asKlassNiz(iUbound) = FormSpecRost.TextBoxKlassNizArm
  asKlassPop(iUbound) = FormSpecRost.TextBoxKlassPopArm
  asKlassSvyzVerh(iUbound) = FormSpecRost.TextBoxKlassSvyzVerhArm
  asKlassSvyzNiz(iUbound) = FormSpecRost.TextBoxKlassSvyzNizArm
  abUsilenie(iUbound) = FormSpecRost.CheckBoxUsilenie.Value
  If abUsilenie(iUbound) = True Then
    aiUsLenght(iUbound) = FormSpecRost.TextBoxUsLenSech
    aiUsShagVerh(iUbound) = FormSpecRost.TextBoxUsShagVerhArm
    aiUsShagNiz(iUbound) = FormSpecRost.TextBoxUsShagNizArm
    aiUsDiamVerh(iUbound) = FormSpecRost.TextBoxUsDiamVerhArm
    aiUsDiamNiz(iUbound) = FormSpecRost.TextBoxUsDiamNizArm
    asUsKlassVerh(iUbound) = FormSpecRost.TextBoxUsKlassVerhArm
    asUsKlassNiz(iUbound) = FormSpecRost.TextBoxUsKlassNizArm
    asUsGostVerh(iUbound) = FormSpecRost.TextBoxUsGOSTVerhArm
    asUsGostNiz(iUbound) = FormSpecRost.TextBoxUsGOSTNizArm
  End If
  
End Sub

Public Function GetParamSech() As Boolean
  'заполнить параметры сечения в форму FormSpecRost
  
  Dim oListItem As ListItem
  Dim i As Integer
  Dim iUbound As Integer
  Dim bolYes As Boolean
  
  'если нет сечений
  If iCountSech = 0 Then
    GetParamSech = False
    Exit Function
  End If
  
  'находим индекс сечения
  For i = 0 To iCountSech - 1
    If asNSech(i) = FormSpecRost.TextBoxNSech Then
      iUbound = i
      bolYes = True
      Exit For
    End If
  Next
  
  'если нет такого сечения
  If bolYes = False Then
    GetParamSech = False
    Exit Function
  End If
  
  'заполняем поля формы
  FormSpecRost.TextBoxNSech = asNSech(iUbound)
  FormSpecRost.TextBoxLenSech = aiLenSech(iUbound)
  FormSpecRost.TextBoxHeightRost = aiHeightRostv(iUbound)
  'FormSpecRost.TextBoxShagDopPopSter = aiShagDopPopSter(iUbound)
  FormSpecRost.TextBoxShagVerhSvyzSter = aiShagSvyzVerh(iUbound)
  FormSpecRost.TextBoxShagNizSvyzSter = aiShagSvyzNiz(iUbound)
  FormSpecRost.TextBoxDiamVerhSvyzSter = aiDiamSvyzVerh(iUbound)
  FormSpecRost.TextBoxDiamNizSvyzSter = aiDiamSvyzNiz(iUbound)
  FormSpecRost.TextBoxVerhZachBet = aiZachBetVerh(iUbound)
  FormSpecRost.TextBoxNizZachBet = aiZachBetNiz(iUbound)
  FormSpecRost.TextBoxKlassVerhArm = asKlassVerh(iUbound)
  FormSpecRost.TextBoxKlassNizArm = asKlassNiz(iUbound)
  FormSpecRost.TextBoxKlassPopArm = asKlassPop(iUbound)
  FormSpecRost.TextBoxKlassSvyzVerhArm = asKlassSvyzVerh(iUbound)
  FormSpecRost.TextBoxKlassSvyzNizArm = asKlassSvyzNiz(iUbound)
  FormSpecRost.CheckBoxUsilenie.Value = abUsilenie(iUbound)
  If abUsilenie(iUbound) = True Then
    FormSpecRost.TextBoxUsLenSech = aiUsLenght(iUbound)
    FormSpecRost.TextBoxUsShagVerhArm = aiUsShagVerh(iUbound)
    FormSpecRost.TextBoxUsShagNizArm = aiUsShagNiz(iUbound)
    FormSpecRost.TextBoxUsDiamVerhArm = aiUsDiamVerh(iUbound)
    FormSpecRost.TextBoxUsDiamNizArm = aiUsDiamNiz(iUbound)
    FormSpecRost.TextBoxUsKlassVerhArm = asUsKlassVerh(iUbound)
    FormSpecRost.TextBoxUsKlassNizArm = asUsKlassNiz(iUbound)
    FormSpecRost.TextBoxUsGOSTVerhArm = asUsGostVerh(iUbound)
    FormSpecRost.TextBoxUsGOSTNizArm = asUsGostNiz(iUbound)
  End If
  
  GetParamSech = True
  
End Function

Attribute VB_Name = "clSetky"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'Класс для объектов типа сетки, содержит свойство имени, шага, диаметра и длину стержней сетки
Option Explicit

Public pbObrab As Boolean 'признак обработки (галочка)
Public psBlName As String
Public psMarka As String 'марка сетки - "С1"
Public piKolSetok As Integer 'кол-во сеток
Public piKolvoBl As Integer 'кол-во блоков сеток (нужно для листвиевера сеток)
Public piKolShtuk As Integer '(шт.3)
Public piShagVertSter As Integer
Public piShagHorSter As Integer
Public piKolShagovHoris As Integer
Public piKolShagovVertik As Integer
Public piKolHorSter As Integer
Public piKolVertSter As Integer
Public piDiamVertSter As Integer
Public piDiamHorSter As Integer
Public psKlassVertSter As String
Public psKlassHorSter As String
Public psGOSTVertSter As String
Public psGOSTHorSter As String
Public psNaimenHorSter As String
Public psNaimenVertSter As String
Public pdMassaEdVertikSter As Double
Public pdMassaEdHorisSter As Double
Public pdMassaSetky As Double
Public psShifrSetki As String
'доп.стержни (вертикальные)
Public pbDopSter As Boolean
Public piDiamDopSter As Integer
Public piLenDopSter As Integer
Public piKolDopSter As Integer
Public psKlassDopSter As String
Public psGOSTDopSter As String
Public psNaimenDopSter As String

Public psError As String

Public piLenghtVertik As Integer
Public piLenghtHoris As Integer

'для сортировки
Public Property Get Name() As String
   Name = psMarka
End Property

Public Sub ObrabBlName(sBlName As String)
  'обработка имени блока сетки вида "Сетка С1(шт.3)"
  
  Dim iValue As Integer
  Dim iLen As Integer
  
  psBlName = sBlName
  
  'марка сетки
  iValue = InStr(LCase(sBlName), "(шт.")
  iLen = Len(pclOptions.psSetkaConst)
  If iValue <> 0 Then
    psMarka = Mid(sBlName, iLen + 2, iValue - (iLen + 2))
    'опр.кол.штук
    piKolShtuk = Val(Mid(sBlName, iValue + 4))
  Else
    psMarka = Mid(sBlName, iLen + 2)
    piKolShtuk = 1
  End If
  
End Sub

Public Sub Raschet()
  'расчет массы сетки
  
  'наименование вертикального стержня
  piLenghtVertik = piShagHorSter * piKolShagovHoris + 50
  psNaimenVertSter = piDiamVertSter & "-" & psKlassVertSter & " " & psGOSTVertSter & _
        " L=" & piLenghtVertik
  'масса 1 вертик стержня
  pdMassaEdVertikSter = Functions.GetMassaDiamPM(piDiamVertSter) * (piLenghtVertik / 1000)
  'кол-во вертик стержней
  piKolVertSter = piKolShagovVertik + 1
  
  'наименование горизонтального стержня
  piLenghtHoris = piShagVertSter * piKolShagovVertik + 50
  psNaimenHorSter = piDiamHorSter & "-" & psKlassHorSter & " " & psGOSTHorSter & _
        " L=" & piLenghtHoris
  'масса 1 горизонтального стержня
  pdMassaEdHorisSter = Functions.GetMassaDiamPM(piDiamHorSter) * (piLenghtHoris / 1000)
  'кол-во горизонтального стержней
  piKolHorSter = piKolShagovHoris + 1
  
  'масса сетки
  pdMassaSetky = pdMassaEdVertikSter * piKolVertSter + pdMassaEdHorisSter * piKolHorSter
  
End Sub

Attribute VB_Name = "clShifr"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
   
   Dim strShifr As String
   Dim strClients As String
   Dim strAdress As String
   Dim strObjectName As String
   Dim strBS As String
   Dim strPart As String
   Dim strPost1 As String
   Dim strPost2 As String
   Dim strPost3 As String
   Dim strPost4 As String
   Dim strFam1 As String
   Dim strFam2 As String
   Dim strFam3 As String
   Dim strFam4 As String

'шифр: например "3085-10"
Public Property Get Shifr() As String
   Shifr = strShifr
End Property
Public Property Let Shifr(ByVal strValue As String)
   strShifr = strValue
End Property

'(бс) - перечень б.с. - (А-К)
Public Property Get BS() As String
   BS = strBS
End Property
Public Property Let BS(ByVal strValue As String)
   strBS = strValue
End Property

'часть - АС
Public Property Get Part() As String
   Part = strPart
End Property
Public Property Let Part(ByVal strValue As String)
   strPart = strValue
End Property

'название фирмы заказчика : ООО"Кронверк-3"
Public Property Get Clients() As String
   Clients = strClients
End Property
Public Property Let Clients(ByVal strValue As String)
   strClients = strValue
End Property

'адресс объекта
Public Property Get Adress() As String
   Adress = strAdress
End Property
Public Property Let Adress(ByVal strValue As String)
   strAdress = strValue
End Property

'Наименование здания : Жилой дом №10
Public Property Get ObjectName() As String
   ObjectName = strObjectName
End Property
Public Property Let ObjectName(ByVal strValue As String)
   strObjectName = strValue
End Property

'должность
Public Property Get Post1() As String
   Post1 = strPost1
End Property
Public Property Let Post1(ByVal strValue As String)
   strPost1 = strValue
End Property

'должность
Public Property Get Post2() As String
   Post2 = strPost2
End Property
Public Property Let Post2(ByVal strValue As String)
   strPost2 = strValue
End Property

'должность
Public Property Get Post3() As String
   Post3 = strPost3
End Property
Public Property Let Post3(ByVal strValue As String)
   strPost3 = strValue
End Property

'должность
Public Property Get Post4() As String
   Post4 = strPost4
End Property
Public Property Let Post4(ByVal strValue As String)
   strPost4 = strValue
End Property

'фамилия
Public Property Get Fam1() As String
   Fam1 = strFam1
End Property
Public Property Let Fam1(ByVal strValue As String)
   strFam1 = strValue
End Property

'фамилия
Public Property Get Fam2() As String
   Fam2 = strFam2
End Property
Public Property Let Fam2(ByVal strValue As String)
   strFam2 = strValue
End Property

'фамилия
Public Property Get Fam3() As String
   Fam3 = strFam3
End Property
Public Property Let Fam3(ByVal strValue As String)
   strFam3 = strValue
End Property

'фамилия
Public Property Get Fam4() As String
   Fam4 = strFam4
End Property
Public Property Let Fam4(ByVal strValue As String)
   strFam4 = strValue
End Property

Attribute VB_Name = "clShpilky"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
   
'все шпильки диаметром 8 A-I
'варьируется только длина
   
  Public piLenght As Integer
  Public piKolvo As Integer
  Public piDiametr As Integer
  Public psKlassArm As String
  Public psGOSTArm As String
  Public psNaimen As String
  Public pdMassaEd As Double
  Public pdMassa As Double
   
Public Sub Obrab()
  'определение наименования шпильки
  'определение массы
  
  psNaimen = "Шпилька из " & piDiametr & "-" & psKlassArm

   'определяем массу одного стержня, кг
   pdMassaEd = GetMassaDiamPM(piDiametr) * (piLenght / 1000)
   'определяем общую массу
   pdMassa = pdMassaEd * piKolvo
  
End Sub
