Attribute VB_Name = "ClassINI"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
 
Private strInI As String
 
'// Win API Declares
Private Declare Function WritePrivateProfileString _
  Lib "kernel32" Alias "WritePrivateProfileStringA" _
 (ByVal lpApplicationName As String, _
  ByVal lpKeyName As Any, _
  ByVal lpString As Any, _
  ByVal lpFileName As String) As Long
 
Private Declare Function GetPrivateProfileString _
  Lib "kernel32" Alias "GetPrivateProfileStringA" _
 (ByVal lpApplicationName As String, _
  ByVal lpKeyName As Any, _
  ByVal lpDefault As String, _
  ByVal lpReturnedString As String, _
  ByVal nSize As Long, _
  ByVal lpFileName As String) As Long
 
Private Function MakePath(ByVal strFileName As String, _
  ByVal strPath As String) As String
 
 '// Makes an INI file: Guarantees a sub dir
 Do While Right$(strPath, 1) = "\"
   strPath = Left$(strPath, Len(strPath) - 1)
 Loop
 
 Do While Left$(strFileName, 1) = "\"
   strFileName = Mid$(strFileName, 2)
 Loop
 
 '// Return the path
 MakePath = strPath & "\" & strFileName
End Function
 
Public Sub CreateIni(strFileName As String, strPath As String)
 '// Make a new ini file
 strInI = MakePath(strFileName, strPath)
End Sub
 
Public Sub WriteFile(strSection As String, _
 strKey As String, _
 strValue As String)
 
 '// Write to strINI
 WritePrivateProfileString strSection, _
   strKey, strValue, strInI
End Sub
 
Public Function GetFile(strSection As String, _
  strKey As String) As String
 
  Dim strTmp As String
  Dim lngRet As String
 
  strTmp = String$(100, 0)
  lngRet = GetPrivateProfileString(strSection, _
    strKey, "", strTmp, _
    Len(strTmp), strInI)
 
  GetFile = StrZ(strTmp)
 
End Function
 
Public Property Let INIFile(ByVal New_IniPath As String)
   'Устанавливаем путь к файлу ini
   strInI = New_IniPath
End Property
Public Property Get INIFile() As String
   INIFile = strInI
End Property
 
 
'v_1.0.0 990630
Private Function StrZ(par As String) As String
Dim nSize As Long, i As Long, Rez As String
   nSize = Len(par)
   i = InStr(1, par, Chr(0)) - 1
   If i > nSize Then i = nSize
   If i < 0 Then i = nSize
   StrZ = Mid(par, 1, i)
End Function

Attribute VB_Name = "Constructs"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

   
   Dim strName As String
   Dim strUniqName As String
   Dim strNaimen As String
   Dim strObozn As String
   Dim dMassa As Double
   Dim intKolvo As Integer


'имя
Public Property Get Name() As String
   Name = strName
End Property
Public Property Let Name(ByVal vNewValue As String)
   strName = vNewValue
End Property

'наименовани
Public Property Get Naimen() As String
   Naimen = strNaimen
End Property
Public Property Let Naimen(ByVal vNewValue As String)
   strNaimen = vNewValue
End Property

'обозначение
Public Property Get Obozn() As String
   Obozn = strObozn
End Property
Public Property Let Obozn(ByVal vNewValue As String)
   strObozn = vNewValue
End Property

'масса - 0.16
Public Property Get Massa() As Double
   Massa = dMassa
End Property
Public Property Let Massa(ByVal vNewValue As Double)
   dMassa = vNewValue
End Property

'кол-во
Public Property Get Kolvo() As Integer
   Kolvo = intKolvo
End Property
Public Property Let Kolvo(ByVal vNewValue As Integer)
   intKolvo = vNewValue
End Property

Attribute VB_Name = "FormMessage"
Attribute VB_Base = "0{9D04F34E-B177-492E-ABF0-11A4B0DBEDAF}{ACCB08AF-3F63-49BE-AFB6-9F2224F03888}"
Attribute VB_GlobalNameSpace = False
Attribute VB_Creatable = False
Attribute VB_PredeclaredId = True
Attribute VB_Exposed = False
Attribute VB_TemplateDerived = False
Attribute VB_Customizable = False
Option Explicit

Private Sub UserForm_Activate()
   hide
   FormMessage.Show vbModeless
End Sub

Private Sub UserForm_Deactivate()
   Label1 = "Выполняется проверка чертежа, подождитте..."
End Sub

Attribute VB_Name = "FormNodesBrack"
Attribute VB_Base = "0{0B132E96-366B-4B77-85E5-BDE9B1630A6A}{AFF3D479-0CA9-47CD-8CE5-4BB63B43FDCA}"
Attribute VB_GlobalNameSpace = False
Attribute VB_Creatable = False
Attribute VB_PredeclaredId = True
Attribute VB_Exposed = False
Attribute VB_TemplateDerived = False
Attribute VB_Customizable = False
Option Explicit

Private Sub cmbExit_Click()
   End
End Sub

Private Sub cmbOK_Click()
   hide
End Sub

Private Sub cmbStop_Click()
   'все по новой
   cmbOK.Visible = False
   cmbStop.Visible = False
   cmbExit.Visible = True
   hide
   FormNodesBrack.Show vbModeless
End Sub

Private Sub cmbView_Click()
   
   Dim objBlock As AcadBlockReference
   Dim index As Integer
   
   index = ListBoxBlocks.ListIndex
   If index = -1 Then
      MsgBox "Не выбран блок!", vbCritical
      Exit Sub
   End If
   index = index + 1
   
   If bolNodeBrackOrDubl = True Then
      Set objBlock = colNodesBrack.Item(index)
   Else
      Set objBlock = colNodesDublObozn.Item(index)
   End If
   
   On Error GoTo HasError
   objBlock.Highlight True
   ZoomCenter objBlock.InsertionPoint, 5000

Exit Sub

HasError:
   MsgBox "Блок был удален!", vbCritical
   'удаляем блок из коллекций
   If bolNodeBrackOrDubl = True Then
      colNodesBrack.Remove index
   Else
      colNodesDublObozn.Remove index
   End If
   'и из листбокса
   ListBoxBlocks.RemoveItem index - 1
   
End Sub

Private Sub UserForm_Activate()

'   Dim objBlock As AcadBlockReference
'
'   ListBoxBlocks.Clear
'
'   'вывести список неопределенных блоков
'   For Each objBlock In colNodesBrack
'      'надеюсь индексы совпадут ????????????????
'      ListBoxBlocks.AddItem objBlock.Name
'   Next
   
End Sub

'Private Sub UserForm_QueryClose(Cancel As Integer, CloseMode As Integer)
'   End
'End Sub

Attribute VB_Name = "FormaFreezeBlock"
Attribute VB_Base = "0{53EA5C93-62C0-4BB8-BF45-176ACC4C3BB1}{AE532262-93AA-4DD8-B716-26681F650818}"
Attribute VB_GlobalNameSpace = False
Attribute VB_Creatable = False
Attribute VB_PredeclaredId = True
Attribute VB_Exposed = False
Attribute VB_TemplateDerived = False
Attribute VB_Customizable = False

Option Explicit

Dim dLeft As Double
Dim dTop As Double

Private Sub ButtonRegen_Click()
   ThisDrawing.Regen acActiveViewport
End Sub

Private Sub ButtonUnFreeze_Click()
   'Разморозка выбранного слоя
   Dim index As Integer
   
   'Проверка выбран ли слой
   index = ListBoxLayers.ListIndex
   
   If index = -1 Then
      MsgBox "Не выбран слой."
      Exit Sub
   End If
   
   Dim sLayerName As String
   sLayerName = ListBoxLayers.Text
   
'   Functions.LoadLayersSate
   
   ThisDrawing.Layers(sLayerName).Freeze = False
   
   Functions.SaveLayersState
   
End Sub

Private Sub ButtonUnFreezeAll_Click()
   'Разморозка всех слоев
   
   If ListBoxLayers.ListCount = 0 Then
      MsgBox "В списке нет слоев"
      Exit Sub
   End If
   
'   Functions.LoadLayersSate
   
   Dim sLayName As String
   Dim i As Integer
   
   For i = 0 To ListBoxLayers.ListCount - 1
      sLayName = ListBoxLayers.List(i)
      ThisDrawing.Layers(sLayName).Freeze = False
   Next
   
   Functions.SaveLayersState
   
End Sub

Private Sub cmbExit_Click()
   
   Dim i As Integer
   Dim objLayer As AcadLayer
   
   'если уже была остановлена прога, то конец
   If cmbOK.Visible = False Then
      'возвращаем заморозку
'      For i = 0 To UBound(FreezeBlocks)
'         Set objLayer = ThisDrawing.Layers.Item(FreezeBlocks(i).LayerName)
'         objLayer.Freeze = True
'      Next
      End
   End If
   
   'скрываем кнопку продолжить
   cmbOK.Visible = False
   
   dLeft = FormaFreezeBlock.Left
   dTop = FormaFreezeBlock.Top
   
   hide
   FormaFreezeBlock.Show vbModeless
   bolFreezeOk = False
   
End Sub

Private Sub cmbOK_Click()
   'возвращаем заморозку слоям и продолжаем прогу
   
   Dim i As Integer
   Dim objLayer As AcadLayer
   Dim intOtvet As Integer
   
'   intOtvet = MsgBox("Слои не будут разморожены!" & vbCrLf & _
'                     "Продолжить?", vbYesNo)
'   If intOtvet = 7 Then 'нет
'      Exit Sub
'   End If
   
   'возвращаем заморозку
'   For i = 0 To UBound(FreezeBlocks)
'      Set objLayer = ThisDrawing.Layers.Item(FreezeBlocks(i).LayerName)
'      objLayer.Freeze = True
'   Next
   
   bolFreezeOk = True
   
   hide
   
End Sub

Private Sub cmbView_Click()
   'подсвечиваем и зуммируем выбранный блок
   
   Dim objBlock As AcadBlockReference
   Dim strCurLayer As String
   Dim strCurBlock As String
   Dim i As Integer
   Dim j As Integer
   Dim index As Integer
   
   On Error GoTo Ошибка
   
   dLeft = FormaFreezeBlock.Left
   dTop = FormaFreezeBlock.Top
   
   'проверяем выделенн ли элемент списка
   If ListBoxBlocks.Text <> "" Then
      strCurLayer = ListBoxLayers.Text
      strCurBlock = ListBoxBlocks.Text
'      If Right(strBlockName, 7) = "заменен" Then
'         strCurBlock = Mid(strCurBlock, 1, Len(strCurBlock) - 8)
'      End If
      index = ListBoxBlocks.ListIndex
      'находим блок в массиве по индексу
      For i = 0 To UBound(FreezeBlocks)
         If FreezeBlocks(i).LayerName = strCurLayer Then
            Set objBlock = FreezeBlocks(i).colBlocks.Item(CStr(index))
            objBlock.Highlight True
            ZoomCenter objBlock.InsertionPoint, 10000
         End If
      Next
      
   End If

Exit Sub

Ошибка:
   If Err.Description = "Объект был стерт" Then
      MsgBox "Объект был стерт"
   Else
      MsgBox Err.Description
   End If
   Resume Next
   
End Sub



Private Sub ListBoxBlocks_Change()
   'записываем выбранный блок
   
   Dim strCurBlock As String
   
   strCurBlock = ListBoxBlocks.Text
   
   TextBoxSelectBlock = strCurBlock
   
End Sub

Private Sub ListBoxBlocks_DblClick(ByVal Cancel As MSForms.ReturnBoolean)
   cmbView_Click
End Sub

Private Sub ListBoxLayers_Change()
   'Для выбранного слоя отобрааем блоки
   
   Dim strCurLayer As String
   Dim i As Integer
   Dim j As Integer
   
   On Error GoTo Ошибка
   
   strCurLayer = ListBoxLayers.Text
   
   ListBoxBlocks.Clear
   
   'находим имя слоя в массиве и заполняем список блоков
   For i = 0 To UBound(FreezeBlocks)
      If FreezeBlocks(i).LayerName = strCurLayer Then
         'записывваем имена блоков
         For j = 0 To FreezeBlocks(i).colBlocks.Count - 1
            ListBoxBlocks.AddItem FreezeBlocks(i).colBlocks.Item(j + 1).Name, CStr(j)
         Next
      End If
   Next
   
   'записываем текущий выбранный слой
   TextBoxSelectLayer = strCurLayer
   
Exit Sub

Ошибка:
   If Err.Description = "Объект был стерт" Then
      MsgBox "Объект был стерт"
      ListBoxBlocks.AddItem "Удалено"
   Else
      MsgBox Err.Description
   End If
   Resume Next

End Sub

Private Sub UserForm_Activate()
   
   If dLeft <> 0 And dTop <> 0 Then
      Me.Left = dLeft
      Me.Top = dTop
   End If
   
End Sub

Private Sub UserForm_Initialize()
   'считываем слои из масива FreezeBlocks
   
   Dim i As Integer
   
   If dLeft <> 0 And dTop <> 0 Then
      Me.Left = dLeft
      Me.Top = dTop
   End If
   
   'выводим список слоев
   For i = 0 To UBound(FreezeBlocks)
      ListBoxLayers.AddItem FreezeBlocks(i).LayerName
   Next
   
End Sub

Attribute VB_Name = "FormaProverky"
Attribute VB_Base = "0{F34BE35B-7E48-4A1C-B0B9-D09C4D0E3DE8}{1ED0F3C3-F523-4D7B-BCEE-87C678D11925}"
Attribute VB_GlobalNameSpace = False
Attribute VB_Creatable = False
Attribute VB_PredeclaredId = True
Attribute VB_Exposed = False
Attribute VB_TemplateDerived = False
Attribute VB_Customizable = False
Option Explicit
   
   'тип текущего списка блоков
   Enum ListBoxType
      ErrName = 0
      Nalog = 1
      Zerkal = 2
      Brack = 3
   End Enum
   
   Dim intListBoxType As Integer
   
Private Sub cmbErrName_Click()
   
   Dim objBlock As AcadBlockReference
   
   ListBoxBlocks.Clear
   
   'вывести список неопределенных блоков
   For Each objBlock In colBlocksErrName
      'надеюсь индексы совпадут ????????????????
      ListBoxBlocks.AddItem objBlock.Name
   Next
   
   intListBoxType = ListBoxType.ErrName
   
End Sub

Private Sub cmbExit_Click()
   End
End Sub

Private Sub cmbOK_Click()
   'все по новой
   bolProverka = True
   hide
End Sub

Private Sub cmbNalog_Click()
   
   Dim objBlock As AcadBlockReference
   
   ListBoxBlocks.Clear
   
   'вывести список неопределенных блоков
   For Each objBlock In colBlocksNalogenie
      'надеюсь индексы совпадут ????????????????
      ListBoxBlocks.AddItem objBlock.Name
   Next
   
   intListBoxType = ListBoxType.Nalog
   
End Sub

Private Sub cmbNeopredel_Click()
   
   Dim objBlock As AcadBlockReference
   
   ListBoxBlocks.Clear
   
   'вывести список неопределенных блоков
   For Each objBlock In colBlockBrack
      'надеюсь индексы совпадут ????????????????
      ListBoxBlocks.AddItem objBlock.Name
   Next
   
   intListBoxType = ListBoxType.Brack
   
End Sub

Private Sub cmbStop_Click()
   'все по новой
   bolProverka = False
   cmbOK.Visible = False
   cmbStop.Visible = False
   cmbExit.Visible = True
   hide
   FormaProverky.Show vbModeless
End Sub

Private Sub cmbView_Click()
   
   Dim objBlock As AcadBlockReference
   Dim index As Integer
   
   index = ListBoxBlocks.ListIndex
   If index = -1 Then
      Exit Sub
   End If
   index = index + 1
   Select Case intListBoxType
      Case ListBoxType.ErrName
         Set objBlock = colBlocksErrName.Item(index)
      Case ListBoxType.Nalog
         Set objBlock = colBlocksNalogenie.Item(index)
      Case ListBoxType.Zerkal
         Set objBlock = colBlocksZerkal.Item(index)
      Case ListBoxType.Brack
         Set objBlock = colBlockBrack.Item(index)
   End Select
   
   On Error GoTo HasError
   objBlock.Highlight True
   ZoomCenter objBlock.InsertionPoint, 10000
   
Exit Sub
   
HasError:
   Select Case Err.Number
      Case -2145386420
         MsgBox "Блок был удален"
         Select Case intListBoxType
            Case ListBoxType.ErrName
               colBlocksErrName.Remove (index)
            Case ListBoxType.Nalog
               colBlocksNalogenie.Remove (index)
            Case ListBoxType.Zerkal
               colBlocksZerkal.Remove (index)
            Case ListBoxType.Brack
               colBlockBrack.Remove (index)
         End Select
         ListBoxBlocks.RemoveItem index
      Case Else
         MsgBox Err.Description, vbCritical
   End Select
   
End Sub

Private Sub cmbZerkal_Click()
   
   Dim objBlock As AcadBlockReference
   
   ListBoxBlocks.Clear
   
   'вывести список неопределенных блоков
   For Each objBlock In colBlocksZerkal
      'надеюсь индексы совпадут ????????????????
      ListBoxBlocks.AddItem objBlock.Name
   Next
   
   intListBoxType = ListBoxType.Zerkal
   
End Sub

Private Sub UserForm_Activate()
   'проверяем коллекции блоков с ошибками и отображаем кнопки
   
   Dim bolYes As Boolean
   
   If colBlocksNalogenie.Count <> 0 Then
      'показываем кнопку
      cmbNalog.Visible = True
      bolYes = True
   End If
   If colBlocksErrName.Count <> 0 Then
      'показываем кнопку
      cmbErrName.Visible = True
      bolYes = True
   End If
   If colBlocksZerkal.Count <> 0 Then
      'показываем кнопку
      cmbZerkal.Visible = True
      bolYes = True
   End If
   If colBlockBrack.Count <> 0 Then
      'показываем кнопку
      cmbNeopredel.Visible = True
      bolYes = True
   End If
   
   If bolYes = True Then
      cmbView.Enabled = True
   End If
   
End Sub

Attribute VB_Name = "FormaRename"
Attribute VB_Base = "0{24F69D0D-98E4-4A3F-9820-F95C7478230D}{7728BD49-380A-4BEF-B264-206D40125441}"
Attribute VB_GlobalNameSpace = False
Attribute VB_Creatable = False
Attribute VB_PredeclaredId = True
Attribute VB_Exposed = False
Attribute VB_TemplateDerived = False
Attribute VB_Customizable = False
Option Explicit

Dim strFileNameOrig As String
Public bolReplace As Boolean

Private Sub cmbRename_Click()
   
   If TextBoxFileName <> strFileNameOrig Then
      bolReplace = False
      hide
   Else
      MsgBox "Вы не изменили имя файла спецификаций!?"
   End If
   
End Sub

Private Sub cmbReplace_Click()
   bolReplace = True
   hide
End Sub

Private Sub UserForm_Activate()
      
   strFileNameOrig = TextBoxFileName
      
End Sub

Private Sub UserForm_QueryClose(Cancel As Integer, CloseMode As Integer)
   End
End Sub

Attribute VB_Name = "FormaShtamp"
Attribute VB_Base = "0{2646DB1D-395B-41D5-B56D-B544DD2F2CA5}{E19A5590-4EBB-4924-9E5E-48F39902F5EA}"
Attribute VB_GlobalNameSpace = False
Attribute VB_Creatable = False
Attribute VB_PredeclaredId = True
Attribute VB_Exposed = False
Attribute VB_TemplateDerived = False
Attribute VB_Customizable = False
Option Explicit
   
   Dim objRecShifr As New ADODB.Recordset

Private Sub CheckBoxOsnKomplect_Click()
   
   On Error GoTo HasError
   
   'если определен шифр
   If objRecShifr.State = 0 Or objRecShifr.BOF = True Then
      MsgBox "Шифр не присвоен чертежу"
      Exit Sub
   End If
   
   If CheckBoxOsnKomplect.Value = True Then
      TextBoxShifr = objRecShifr!Шифр & objRecShifr!БС & "-" & objRecShifr!Часть
   Else
      TextBoxShifr = objRecShifr!Шифр & "-" & objRecShifr!Часть
   End If

Exit Sub
HasError:
End Sub

Private Sub CheckBoxSpecNodes_Click()
   
   If CheckBoxSpecNodes.Value = True Then
      'запрос серий из базы
      Dim objCommand As New ADODB.Command
      Dim objRecSet As New ADODB.Recordset
      Dim strConect As String
      Dim strSQL As String
      Dim strMacroFolder As String
      Dim strNodeDWGFullPath As String
      Dim objBlNode As AcadBlockReference
      Dim varPt As Variant
      Dim varAtr As Variant
      Dim objAtr As AcadAttributeReference
      Dim strLayer As String
      Dim strDBNodes As String
      Dim i As Integer
      
      On Error GoTo HasError
      
      'подлючение к базе
      If objConect.State = adStatusOK Then objConect.Close
      
      'строка подключения
      If Not objConect.State = adStatusOK Then
         strDBNodes = strBDNodesFolder & "\Базы\dbNodes.mdb"
         strConect = strProvider & _
                  "Data Source=" & strDBNodes
         'подключение
         objConect.Mode = adModeRead
         objConect.Open strConect
      End If
         
      'запрос серий
      If objRecSet.State = adStateOpen Then objRecSet.Close
      strSQL = "SELECT * FROM Серии WHERE Ser <> 'Типовые';"
      objRecSet.Open Source:=strSQL, ActiveConnection:=objConect, _
               CursorType:=adOpenKeyset, LockType:=adLockOptimistic, Options:=adCmdText
      'заполняем комбобок серий
      If objRecSet.EOF And objRecSet.BOF Then
         MsgBox "Серий нет! Создайте серию в каталоге узлов!", vbCritical
         Exit Sub
      End If
      objRecSet.MoveFirst
      ComboBoxNodesSer.Clear
      Do Until objRecSet.EOF
         ComboBoxNodesSer.AddItem objRecSet!Ser
         objRecSet.MoveNext
      Loop
      ComboBoxNodesSer.Enabled = True
   Else
      ComboBoxNodesSer.Enabled = False
   End If

Exit Sub
HasError:
      MsgBox Err.Description, vbCritical
      CheckBoxSpecNodes.Value = False
      
End Sub

Private Sub cmbExit_Click()
   End
End Sub

Private Sub cmbOK_Click()
   
   'если стоит галка для подсчета узлов, то проверяем выбрана ли серия и подтверждаем
   If CheckBoxSpecNodes.Value = True Then
      If ComboBoxNodesSer.ListIndex = -1 Then
         MsgBox "Не выбрана серия: Крон,Куз,Крон17!", vbCritical
         Exit Sub
      Else
         If MsgBox("Подтвердите, что серия = " & ComboBoxNodesSer, vbExclamation + vbYesNo) = vbNo Then
            Exit Sub
         End If
      End If
   End If
   
   'запись фамилии пользователя в ини
   If TextBoxFam5 <> "" Then
      Functions.SetUserFamily TextBoxFam5
   End If
   
   hide
   
End Sub

Private Sub UserForm_Activate()
   'получаем данные о шифре этого чертежа
   Dim strConect As String
   Dim strShifr As String
   Dim strSQL As String
   Dim strShifrMacroPath As String
   Dim intValue As Integer
   
'   Dim colShifr As Collection
'   Dim objShifr As clShifr
   
   On Error GoTo HasError
   
   LabelDrawPath = "Текущий чертеж: " & ThisDrawing.FullName
   
   'определяем фамилию пользователя
   TextBoxFam5 = Functions.GetUserFamily
   
   'получаем объект словаря
   '"SpecKonstr"-название словаря, в чертеже
   '"Штамп"-название XRecord записи в словаре
   strShifr = Functions.GetShifrFromDict
   If strShifr = "" Then
      'нечего определять
      MsgBox "Шифр для этого чертежа не присвоен."
      CheckBoxOsnKomplect.Visible = False
      Exit Sub
   End If
   
   'получаем коллекцию шифров
'   Set colShifr = Functions.GetColShifFromTXT(strShifrTxtFullPath)
'   Set objShifr = colShifr.Item(strShifr)
'   If objShifr Is Nothing Then
'      'шифр не найден в каталоге шифров, показываем форму с полями по умолчанию
'      MsgBox "Шифр этого чертеж - " & strShifr & vbCrLf & _
'            "В каталоге шифров такого нет."
'      Exit Sub
'   End If
   strShifrMacroPath = Functions.GetMacroFolder(psVBProjectName)
   'intValue = InStrRev(strShifrMacroPath, "\")
   'strShifrMacroPath = VBA.Left(strShifrMacroPath, intValue)
   strShifrMacroPath = strShifrMacroPath & "\Базы\Шифры.mdb"
   If objConect.State = adStateOpen Then objConect.Close
      'строка подключения
      strConect = strProvider & _
               "Data Source=" & strShifrMacroPath
      'подключение
      objConect.CursorLocation = adUseClient
      objConect.Mode = adModeWrite  'дугие смогут тоже подключатьься
      objConect.Open strConect
   
   'запрос шифра
   If objRecShifr.State = adStateOpen Then objRecShifr.Close
   strSQL = "SELECT * FROM Шифры WHERE Шифр = '" & strShifr & "'"
   objRecShifr.Open Source:=strSQL, ActiveConnection:=objConect, _
                  CursorType:=adOpenKeyset, LockType:=adLockOptimistic, Options:=adCmdText
   If objRecShifr.EOF And objRecShifr.BOF Then
      MsgBox "Не найден шифр в катологе!", vbExclamation
      Exit Sub
   End If
   
   'заполнение полей формы из полученного шифра
   TextBoxShifr = objRecShifr!Шифр & "-" & objRecShifr!Часть
   TextBoxZakaz = objRecShifr!Заказчик
   TextBoxAdress = objRecShifr!Адрес
   TextBoxNomerDoma = objRecShifr!Наимен_объекта
   TextBoxPost1 = objRecShifr!Должность1
   TextBoxPost2 = objRecShifr!Должность2
   TextBoxPost3 = objRecShifr!Должность3
   TextBoxPost4 = objRecShifr!Должность4
   TextBoxFam1 = Functions.GetFamilWithoutInitial(objRecShifr!Фамилия1)
   TextBoxFam2 = Functions.GetFamilWithoutInitial(objRecShifr!Фамилия2)
   TextBoxFam3 = Functions.GetFamilWithoutInitial(objRecShifr!Фамилия3)
   TextBoxFam4 = Functions.GetFamilWithoutInitial(objRecShifr!Фамилия4)
   If objRecShifr!БС = "" Then
      CheckBoxOsnKomplect.Visible = False
   Else
      CheckBoxOsnKomplect.Visible = True
      CheckBoxOsnKomplect.Value = False
   End If
   TextBoxStage = objRecShifr!Стадия
   
   'сообщение об удачном считывании данных из каталога шифров
   MsgBox "Данные успешно считаны из каталога шифров!"
Exit Sub
HasError:
   Select Case Err.Number
      Case 94
         Resume Next
      Case 52252454 'ключ не найден
         Resume Next
      Case Else
         MsgBox "FormaShtamp, UserForm_Initialize" & vbCrLf & _
            Err.Description
   End Select
   
End Sub

Private Sub UserForm_Initialize()
   
   'записываем серии узлов в комбобоксе
'   ComboBoxNodesSer.AddItem "Крон"
'   ComboBoxNodesSer.AddItem "Куз"
'   ComboBoxNodesSer.AddItem "Крон17"
   
'   'запрос серий из базы
'   Dim objCommand As New ADODB.Command
'   Dim objRecSet As New ADODB.Recordset
'   Dim strConect As String
'   Dim strSQL As String
'   Dim strMacroFolder As String
'   Dim strNodeDWGFullPath As String
'   Dim objBlNode As AcadBlockReference
'   Dim varPt As Variant
'   Dim varAtr As Variant
'   Dim objAtr As AcadAttributeReference
'   Dim strLayer As String
'   Dim strDBNodes As String
'   Dim i As Integer
'
'   On Error GoTo HasError
'
'   'подлючение к базе
'   If objConect.State = adStatusOK Then objConect.Close
'
'   'строка подключения
'   If Not objConect.State = adStatusOK Then
'      strDBNodes = strBDNodesFolder & "\dbNodes.mdb"
'      strConect = strProvider & _
'               "Data Source=" & strDBNodes
'      'подключение
'      objConect.Mode = adModeRead
'      objConect.Open strConect
'   End If
'
'   'запрос серий
'   If objRecSet.State = adStateOpen Then objRecSet.Close
'   strSQL = "SELECT * FROM Серии WHERE Ser <> 'Типовые';"
'   objRecSet.Open Source:=strSQL, ActiveConnection:=objConect, _
'            CursorType:=adOpenKeyset, LockType:=adLockOptimistic, Options:=adCmdText
'   'заполняем комбобок серий
'   If objRecSet.EOF And objRecSet.BOF Then
'      MsgBox "Серий нет! Создайте серию в каталоге узлов!", vbCritical
'      Exit Sub
'   End If
'   objRecSet.MoveFirst
'   Do Until objRecSet.EOF
'      ComboBoxNodesSer.AddItem objRecSet!Ser
'      objRecSet.MoveNext
'   Loop
'
'Exit Sub
'HasError:
'      MsgBox Err.Description, vbCritical
   
End Sub

Private Sub UserForm_QueryClose(Cancel As Integer, CloseMode As Integer)
   End
End Sub

Attribute VB_Name = "Functions"
Option Explicit

Public Function GetMacroFolder(strVBProjectName) As String
   'получение пути к корню макроса
   'без \
   
   Dim strMacroFolder As String
   Dim intValue As Integer
   
   On Error GoTo HasError
   
   strMacroFolder = Application.VBE.vbprojects.Item(strVBProjectName).FileName
   intValue = InStrRev(strMacroFolder, "\")
   strMacroFolder = Left(strMacroFolder, intValue - 1) 'корень с макросом, без \ на конце
   
   GetMacroFolder = strMacroFolder
   
Exit Function

HasError:
   Select Case Err.Number
      Case Else
         MsgBox "Functions, GetMacroFolder" & vbCrLf & _
               Err.Description
   End Select
   
End Function

'Public Function GetColShifFromTXT(ShifrTXTFullPath As String) As Collection
'   'считываем строки из файла и заполняем коллекцию объектами шифра
'
'   Dim colShifr As New Collection
'   Dim objShifr As clShifr
'   Dim strShifr As String
'   Dim strValue As String
'   Dim intValue As Integer
'
'   'форма записы шифра:
'   '3085-10;Купряхин А.П.;ЗАО"Кронверк-3";Шурова Гора 7, в Ленинском районе г.Саратова;Жилой дом №10
'
'   If Dir(ShifrTXTFullPath) = "" Then
'      'возвращаем Nothing
'      Exit Function
'   End If
'
'   Close #1
'   'через открытие файла
'   Open ShifrTXTFullPath For Input Access Read As #1
'   'чтение файла
'   While Not EOF(1)
'      Set objShifr = New clShifr
'      Line Input #1, strShifr
'      'до первого ; - шифр
'      intValue = InStr(strShifr, ";")
'      strValue = Left(strShifr, intValue - 1)
'      objShifr.Shifr = strValue
'      strShifr = Mid(strShifr, intValue + 1) 'сокращаем строчку до первого ; включительно
'      'до второго ; - бс
'      intValue = InStr(strShifr, ";")
'      strValue = Left(strShifr, intValue - 1)
'      objShifr.BS = strValue
'      strShifr = Mid(strShifr, intValue + 1)
'      'до след ; - часть
'      intValue = InStr(strShifr, ";")
'      strValue = Left(strShifr, intValue - 1)
'      objShifr.Part = strValue
'      strShifr = Mid(strShifr, intValue + 1)
'      'до след ; - ГИП
'      intValue = InStr(strShifr, ";")
'      strValue = Left(strShifr, intValue - 1)
'      objShifr.GIP = strValue
'      strShifr = Mid(strShifr, intValue + 1)
'      'след ; - заказчик
'      intValue = InStr(strShifr, ";")
'      strValue = Left(strShifr, intValue - 1)
'      objShifr.Clients = strValue
'      strShifr = Mid(strShifr, intValue + 1)
'      'след ; - адресс
'      intValue = InStr(strShifr, ";")
'      strValue = Left(strShifr, intValue - 1)
'      objShifr.Adress = strValue
'      strShifr = Mid(strShifr, intValue + 1)
'      'след ; - наименование объекта
'      intValue = InStr(strShifr, ";")
'      strValue = Left(strShifr, intValue - 1)
'      objShifr.ObjectName = strValue
'      strShifr = Mid(strShifr, intValue + 1)
'      'след ; - должность нач.отдела
'      intValue = InStr(strShifr, ";")
'      strValue = Left(strShifr, intValue - 1)
'      objShifr.FieldNachOtd = strValue
'      strShifr = Mid(strShifr, intValue + 1)
'      'след ;  - фамилия нач.отдела
'      intValue = InStr(strShifr, ";")
'      strValue = Left(strShifr, intValue - 1)
'      objShifr.FamNachOtd = strValue
'      strShifr = Mid(strShifr, intValue + 1)
'      'след фамилия Гл.специалиста
'      objShifr.GlSpec = strShifr
'      'добавляем объект в коллекцию
'      colShifr.Add objShifr, objShifr.Shifr
'   Wend
'   Close #1
'
'   Set GetColShifFromTXT = colShifr
'
'End Function



Public Function GetShifrFromDict() As String
   'чтение записи шифра из словаря
   'словарь SPD
   'запись Shifr
   'если нет словаря или записи, возвращает ""
   
   Dim objDict As AcadDictionary
   Dim objXRec As AcadXRecord
   Dim XRDataType As Variant
   Dim XRDataValue As Variant
   
   On Error GoTo HasError
   
   'получаем словарь чертежа
   Set objDict = ThisDrawing.Dictionaries.Item("SPD")
   'получаем запись SPD из словаря
   Set objXRec = objDict.Item("Shifr")
   'считываем данные записи
   objXRec.GetXRecordData XRDataType, XRDataValue
   
   If IsEmpty(XRDataValue) = True Then
      GetShifrFromDict = ""
      Exit Function
   Else
      GetShifrFromDict = XRDataValue(0)
      Exit Function
   End If

Exit Function

'обработка шибок
HasError:
   Select Case Err.Number
      Case "-2145386476" 'Ключ не найден
         'если нет записи
         'возвращаем пустую строчку
'         MsgBox "Ключ не найден"
         GetShifrFromDict = ""
         Exit Function
      Case Else
         MsgBox "Функция GetShifrFromDict - " & Err.Description
         GetShifrFromDict = False
         Exit Function
   End Select
   
Resume Next
   
End Function

Public Function GetColBlockName(strBlockName As String) As Collection
   'возвращает коллекцию блоков заданного имиени в черткеже
   
   Dim selBlocks As AcadSelectionSet
   Dim objBlockRef As AcadBlockReference
   Dim intFT(1) As Integer
   Dim varFD(1) As Variant
   
   'создаем набор
   Set selBlocks = GetSelSet("Блоки")
   
   'задаем фильтр
   intFT(0) = 0: varFD(0) = "insert"
   intFT(1) = 2: varFD(1) = strBlockName
   
   selBlocks.Select acSelectionSetAll, , , intFT, varFD
   
   If selBlocks.Count = 0 Then
      Set GetColBlockName = Nothing
   Else
      Set GetColBlockName = New Collection
      For Each objBlockRef In selBlocks
         GetColBlockName.Add objBlockRef
      Next
   End If
   
End Function

Public Function GetSelSet(strSelName As String) As AcadSelectionSet
   'возвращает набор, с заданным именем
   'если набор с таким именем был, он очищается
   
   On Error GoTo HasError
   Set GetSelSet = ThisDrawing.SelectionSets.Item(strSelName)
   GetSelSet.Clear
   
Exit Function

HasError:
   Set GetSelSet = ThisDrawing.SelectionSets.Add(strSelName)
   
End Function

Public Function GetFamilWithoutInitial(strFamil As String) As String
   'возвращает строку фамилии без инициалов
   'разделителем фамилии и инициалов может быть или " " или прописная буква
   
   Dim intLen As Integer
   Dim strSymbol As String
   Dim i As Integer
   
   intLen = InStr(strFamil, " ")
   
   'если есть пробел, то значит это пробел между фамилией и инициалами
   If intLen <> 0 Then
      GetFamilWithoutInitial = Left(strFamil, intLen - 1)
   Else
      GetFamilWithoutInitial = strFamil
   End If
   
End Function


Public Function AddBlocksFromDWG(strDwgFileFullPath) As Boolean
   'внедрение определений блоков из внешнего файла в текущий чертеж
   
   Dim dPt(2) As Double
   Dim objXref As AcadExternalReference
   Dim strValue As String
   Dim intValue As Integer
   
   On Error Resume Next
   
   'проверяем существование указанного файла
   If Dir(strDwgFileFullPath) = "" Then
      AddBlocksFromDWG = False
      Exit Function
   End If
   'проверка имени текущего чертежа и вставляемого
      'вставляем ссылку
      Set objXref = objMS.AttachExternalReference(strDwgFileFullPath, "Name_", dPt, 1, 1, 1, 0, False)
      objMS.Blocks.Item(objXref.Name).Bind True
      objXref.Delete
      objMS.Blocks.Item("Name_").Delete
   
   AddBlocksFromDWG = True
   
End Function

Public Function GetDetFromBase(strNodeName As String, strNodeObozn As String, sSer As String) As Collection
   'получение данных по деталям для заданного имени узла, и заданной серии
   
   Dim strSQL As String
   Dim recDetail As New ADODB.Recordset
   Dim objDetail As Constructs
   Dim strSer As String
   Dim lNode_ID As Long
   
   On Error GoTo HasError
   
   'запрос имени серии для данного обозначения
   strSQL = "SELECT Ser FROM Серии, Альбомы WHERE Альбомы.Ser_ID = Серии.ID AND Альбомы.Obozn = '" & strNodeObozn & "'"
   recDetail.Open Source:=strSQL, ActiveConnection:=objConect, _
            CursorType:=adOpenStatic, LockType:=adLockReadOnly, Options:=adCmdText
   If recDetail.EOF And recDetail.BOF Then
      'заносим блок узла в коллекцию ошибочных узлов
      Exit Function
   End If
   recDetail.MoveFirst
   'если серия узла не соответствует серии расчитываемого чертежа (в FormaShtamp.ComboBoxNodesSer)
   strSer = recDetail!Ser
   If sSer <> strSer And strSer <> "Типовые" Then
      'заносим блок узла в коллекцию ошибочных узлов
      Exit Function
   End If
   recDetail.Close
   
   'запрос ID узла
   If strSer = "Типовые" Then
      strSQL = "SELECT ID FROM Типовые_узлы WHERE Obozn = '" & strNodeObozn & "' AND Name = '" & strNodeName & "';"
   Else
      strSQL = "SELECT ID FROM Узлы WHERE Obozn = '" & strNodeObozn & "' AND Name = '" & strNodeName & "';"
   End If
   recDetail.Open Source:=strSQL, ActiveConnection:=objConect, _
         CursorType:=adOpenStatic, LockType:=adLockReadOnly, Options:=adCmdText
   If recDetail.EOF And recDetail.BOF Then
      'такого узла нет
      Exit Function
   End If
   lNode_ID = recDetail!ID
   recDetail.Close
   'запрос состава узла с данными по деталям
   If strSer = "Типовые" Then
      strSQL = "SELECT Изделия.Name, Изделия.Massa, Изделия.Obozn, Изделия.Naimen, Типовые_состав.Range " & _
            "FROM Изделия INNER JOIN Типовые_состав ON Изделия.ID = Типовые_состав.Detail_ID " & _
            "WHERE Типовые_состав.Node_ID = " & lNode_ID
   Else
      strSQL = "SELECT Изделия.Name, Изделия.Massa, Изделия.Obozn, Изделия.Naimen, Состав.Range " & _
            "FROM Изделия INNER JOIN Состав ON Изделия.ID = Состав.Detail_ID " & _
            "WHERE Состав.Node_ID = " & lNode_ID
   End If
'   strSQL = "SELECT Изделия.Name, Изделия.Massa, Изделия.Obozn, Изделия.Naimen, " & strSer & "_состав.Range " & _
'         "FROM Изделия INNER JOIN (" & strSer & "_узлы INNER JOIN " & strSer & "_состав ON " & strSer & "_узлы.ID = " & strSer & "_состав.Node_ID) ON Изделия.ID = " & strSer & "_состав.Detail_ID " & _
'         "WHERE " & strSer & "_узлы.Name = '" & strNodeName & "' AND " & strSer & "_узлы.Obozn = '" & strNodeOboz
   recDetail.Open Source:=strSQL, ActiveConnection:=objConect, _
            CursorType:=adOpenStatic, LockType:=adLockReadOnly, Options:=adCmdText
   If recDetail.EOF And recDetail.BOF Then
      'нет деталей в узле
      'надо как то передать это в основную процедуру
      Set GetDetFromBase = New Collection
      Exit Function
   End If
   
   Set GetDetFromBase = New Collection
   
   'заполняем коллек
   recDetail.MoveFirst
   Do While Not recDetail.EOF
      Set objDetail = New Constructs
      objDetail.Name = recDetail!Name
      objDetail.Naimen = recDetail!Naimen
      objDetail.Obozn = recDetail!Obozn
      objDetail.Massa = recDetail!Massa
      objDetail.Kolvo = recDetail!Range
      GetDetFromBase.Add objDetail
      recDetail.MoveNext
   Loop
   
Exit Function
HasError:
   MsgBox Err.Description, vbCritical
   
End Function

Public Function SetUserFamily(sFamely As String)
   'запись фамилии юзера(по имени компьютера SPD-26)
   
   Dim oUserIni As New ClassINI
   Dim sMacroFolder As String
   Dim sUserName As String 'имя пользователя
   
   On Error GoTo HasError
   
   'определение имени пользоваттеля
   sUserName = WinAPI.ComputerName
   
   'определяем ини файл
   sMacroFolder = GetMacroFolder(psVBProjectName)
   
   oUserIni.CreateIni "User.ini", sMacroFolder & "\Ini"
   
   oUserIni.WriteFile "User", sUserName, sFamely

Exit Function
HasError:
   MsgBox Err.Description, vbCritical
   
End Function

Public Function GetUserFamily() As String
   'определение фамилии юзера(по имени компьютера SPD-26) из ини файла User.ini
   
   Dim oUserIni As New ClassINI
   Dim sMacroFolder As String
   Dim sUserName As String 'имя пользователя
   
   On Error GoTo HasError
   
   'определение имени пользоваттеля
   sUserName = WinAPI.ComputerName
   
   'определяем ини файл
   sMacroFolder = GetMacroFolder(psVBProjectName)
   
   oUserIni.CreateIni "User.ini", sMacroFolder & "\Ini"
   
   GetUserFamily = oUserIni.GetFile("User", sUserName)

Exit Function
HasError:
   MsgBox Err.Description, vbCritical
   
End Function

Public Function SaveLayersState()
  'Сохранение состояния слоев
  
  Dim oAcLayerManager As AcadLayerStateManager
  
  On Error Resume Next
  
  Set oAcLayerManager = ThisDrawing.Application.GetInterfaceObject("AutoCAD.AcadLayerStateManager.17")
  oAcLayerManager.SetDatabase ThisDrawing.Database
  
  oAcLayerManager.Delete "SpecKonstr"
  oAcLayerManager.Save "SpecKonstr", acLsFrozen + acLsOn + acLsLocked
  
End Function

Public Function LoadLayersSate()
  'Восстановление состояния слоев
  
  Dim oAcLayerManager As AcadLayerStateManager
  
  On Error Resume Next
  
  Set oAcLayerManager = ThisDrawing.Application.GetInterfaceObject("AutoCAD.AcadLayerStateManager.17")
  oAcLayerManager.SetDatabase ThisDrawing.Database
  
  oAcLayerManager.Restore "SpecKonstr"
  oAcLayerManager.Delete "SpecKonstr"
  
End Function

Attribute VB_Name = "Main"
Option Explicit
   
   Public Const psVBProjectName As String = "SpecKonstr"
   Public Const strProvider As String = "Provider=Microsoft.Jet.OLEDB.4.0;"
   
   Public objConect As New ADODB.Connection
   
   Public objDoc As New AXDBLib.AxDbDocument
   Public objMS As AXDBLib.AcadModelSpace
   
   Public strTableFullPath As String
   
   'жесткое(плохо,очень плохо так делать) задание пути к (временному файлу статуса редактирования базы шифра.)?????????
   Public Const strShifrTxtFullPath As String = "\\Sgpsrv2\СПД\Конструкторы\Макросы\Шифры\Shifr.txt"
   'путь к файлу со штампами
   Public Const strStampsDwgFullPath As String = "\\Sgpsrv2\СПД\Конструкторы\Макросы\Штампы.dwg"

'   Type Constructs
'      Name As String
'      Naimenovanie As String
'      Oboznachenie As String
'      Kol As Integer
'      Massa As Integer
'   End Type
   
   Public Declare Function GetAsyncKeyState Lib "user32" (ByVal vKey As Long) As Integer
   Public Const VK_ESCAPE = &H1B
'   Dim typeConstructs() As Constructs
   Dim typeDungeons As New Collection ' Constructs
   Dim typeElevs As New Collection ' Constructs
   Dim typeRoofs As New Collection ' Constructs
   
   Const strSelSetDungeons As String = "Техподполье"
   Const strSelSetElevation As String = "Этажи"
   Const strSelSetRoof As String = "Чердак"
   
'   Dim colDetailDungeon As New Collection
'   Dim colDetailElev As New Collection
'   Dim colDetailRoof As New Collection
   
   Dim typeDetailDungeon As New Collection ' Constructs
   Dim typeDetailElev As New Collection ' Constructs
   Dim typeDetailRoof As New Collection ' Constructs
   
   Dim bolArrayDungeon As Boolean
   Dim bolArrayElev As Boolean
   Dim bolArrayRoof As Boolean
   
   Dim dPtInsertTable(2) As Double 'текущая точка вставленной таблицы
   
   Enum Format
      A2 = 1
      A3 = 2
      A4 = 3
   End Enum

   Enum DrawingNaimen
      Dungeon = 1 '"Спецификация ж. б. изделий техподполья"
      Elev = 2 ' "Спецификация ж. б. изделий этажей"
      Roof = 3 ' "Спецификация ж. б. изделий чердака"
      DetDungeon = 4 '"Спецификация ж. б. изделий техподполья"
      DetElev = 5 ' "Спецификация ж. б. изделий этажей"
      DetRoof = 6 ' "Спецификация ж. б. изделий чердака"
      Nodes = 7 ' "Спецификация узлов"
   End Enum
   
   Enum TypeConstrEnum
      GB = 0
      Node = 1
   End Enum
   
   Dim intNomerDobLista As Integer
   
   Type FreezeBlock
      LayerName As String
      colBlocks As Collection
      IsBlocks As Boolean
   End Type
   
   Public FreezeBlocks() As FreezeBlock  'массив замороженных слоев и блоков на них
   Public bolFreezeOk As Boolean
   
   Public colBlocksNalogenie As New Collection
   Public colBlocksZerkal As New Collection  'зеркальные блоки при проверке
   Public colBlocksErrName As New Collection  'блоки у которых значение атрибута марки не равно имени блока
   Public bolProverka As Boolean
   
   Dim colNodeBlocksBuffer As New Collection
   
   Public colNodesBrack As New Collection
   Public colNodesDublObozn As New Collection
   Public bolNodeBrackOrDubl As Boolean
   
   Public colBlockBrack As New Collection  'перечень забракованных блоков (т.е. не блоков жб. изделий)
   
   Public strBDNodesFolder As String 'путь к папке с базой узлов \\Sgpsrv2\СПД\Конструкторы\Макросы\BaseNodes

      
Public Sub Main()
   
   Dim strValue As String
   Dim intVersion As Integer
   Dim intOtvet As Integer
   
   Erase FreezeBlocks
   bolFreezeOk = False
   Set colBlocksNalogenie = Nothing
   Set colBlocksZerkal = Nothing
   Set colBlocksErrName = Nothing
   Set colBlockBrack = Nothing
   Set colNodesBrack = Nothing
   Set colNodesDublObozn = Nothing
   bolProverka = False
   
'   intVersion = Val(Version)
'   'проверка версии акада, если не 2008 то, предупреждение
'   If intVersion <> 17 Then
'      intOtvet = MsgBox("Предупреждаю программа расчитана на 2008 автокад." & vbCrLf & _
'            "Текущая верcия - " & Version & vbCrLf & _
'            "Продолжить?", vbYesNo)
'      If intOtvet = 7 Then
'         Exit Sub
'      End If
'   End If
   
   'если текущий чертеж не сохранен на диске, то так нельзя
   If ThisDrawing.FullName = "" Then
      MsgBox "Текущий чертеж не сохранен на диске!" & vbCrLf & _
            "В корне с чертежом будет сохраняться спецификация.", vbCritical
      End
   End If
   
   'проверка доступна ли база узлов, т.е. не редактирует ли ее кто в данное время
   strValue = ProvBaseNodeState
   If strValue <> "" Then
      'предупреждение о том что база узлов сейчас редактируется,
      If MsgBox("База узлов сейчас открыта, пользователем:" & vbCrLf & strValue & vbCrLf & "Продолжиь?", vbInformation + vbYesNo) = vbNo Then
         'выход
         End
      End If
   End If
   
   'Сохранение состояния слоев
   Functions.SaveLayersState
   
   'проверка наличия блоков изделия на замороженных слоях
   If ProvBlockIzdOnFreezeLayers = False Then
      'если нажали выйти из проги
      'Восстановление состояния слоев
      Functions.LoadLayersSate
      End
   End If
   
   'Восстановление состояния слоев
   Functions.LoadLayersSate
   
'   'проверка всех блоков на чертеже
'   ProvAllBlocksInDraw
'   Dim bolProverka As Boolean
    bolProverka = False 'входное значение
   'все проверки, и занесение ошибочных блоков в коллекции
   AllProverks
   'если найдены ошибки отображаем форму
   If bolProverka = True Then
      'форма для исправлений
      FormaProverky.Show
      If bolProverka = False Then
         Exit Sub
      End If
   End If
      
   'создание наборов
   MakeSelSets
   
   'заполнение штампа
   FormaShtamp.Show
   
   'создание массивов с блоками
   'и коллекций узлов
   MakeColOfTypeConstructions
   
   Dim objBlock As AcadBlockReference
   Dim varAtr As Variant
   Dim objAtr As AcadAttributeReference
   
   If colNodesDublObozn.Count <> 0 Then
      'значит есть блоки узлов с одним именем но с разным обозначением
      FormNodesBrack.ListBoxBlocks.Clear
      'вывести список неопределенных блоков
      For Each objBlock In colNodesDublObozn
         'надеюсь индексы совпадут ????????????????
         For Each varAtr In objBlock.GetAttributes
            If LCase(varAtr.TagString) = "марка" Then
               FormNodesBrack.ListBoxBlocks.AddItem varAtr.TextString
               Exit For
            End If
         Next
      Next
      FormNodesBrack.LabelText = "Узлы с одним именем но с разными обозначениями!"
      bolNodeBrackOrDubl = False
      FormNodesBrack.cmbStop.Visible = False
      FormNodesBrack.cmbOK.Visible = False
      FormNodesBrack.cmbExit.Visible = True
      FormNodesBrack.Show vbModeless
      GoTo Конец
   End If
   
   'создание файла спецификации жб изделий
   'и файла спецификации узлов "Спец.узлы б.с."А","Б""
   MakeSpecif
   
   'если есть ненайденые узлы по базе, то показываем форму с отчетом
   If colNodesBrack.Count <> 0 Then
      FormNodesBrack.ListBoxBlocks.Clear
      'вывести список неопределенных блоков
      For Each objBlock In colNodesBrack
         'надеюсь индексы совпадут ????????????????
         For Each varAtr In objBlock.GetAttributes
            If LCase(varAtr.TagString) = "марка" Then
               FormNodesBrack.ListBoxBlocks.AddItem varAtr.TextString
               Exit For
            End If
         Next
      Next
      FormNodesBrack.LabelText = "Блоки узлов не найденные в каталоге узлов!"
      bolNodeBrackOrDubl = True
      FormNodesBrack.cmbStop.Visible = False
      FormNodesBrack.cmbOK.Visible = False
      FormNodesBrack.cmbExit.Visible = True
      FormNodesBrack.Show vbModeless
      GoTo Конец
   End If
   
   'предложение открыть спецификацию
   If MsgBox("Cпецификация готова и сохранена в: " & vbCrLf & strTableFullPath & vbCrLf & "Открыть?", vbYesNo + vbQuestion) = vbYes Then
      AutoCAD.Documents.Open strTableFullPath
   End If
   
   End

Конец:
   
End Sub

Private Sub MakeSelSets()
   
   Dim selSetDungeons As AcadSelectionSet
   Dim selSetElevations As AcadSelectionSet
   Dim selSetRoof As AcadSelectionSet
   Dim intOtvet As Integer
   Dim varPt1 As Variant
   Dim varPt2 As Variant
   Dim intFilterType(1) As Integer
   Dim varFilterDate(1) As Variant
   Dim objSelSet As AcadSelectionSet
   Dim bolVybor As Boolean
   
   On Error Resume Next
   
   'создаем наборы
   Set selSetDungeons = Functions.GetSelSet(strSelSetDungeons)
   Set selSetElevations = Functions.GetSelSet(strSelSetElevation)
   Set selSetRoof = Functions.GetSelSet(strSelSetRoof)
   
   intFilterType(0) = 0: intFilterType(1) = 66
   varFilterDate(0) = "insert": varFilterDate(1) = 1
   
   'набор для элементов техподполья
   If MsgBox("Выбрать элементы техподполья?", vbYesNo, psVBProjectName) = vbYes Then
      bolVybor = False
    Do
      selSetDungeons.Clear
      varPt1 = ThisDrawing.Utility.GetPoint(, "Выбор объектов для спецификации техподполья. Первая точка рамки:")
      varPt2 = ThisDrawing.Utility.GetCorner(varPt1, "Вторая точка рамки")
      ZoomWindow varPt1, varPt2
      selSetDungeons.Select acSelectionSetCrossing, varPt1, varPt2, intFilterType, varFilterDate
      If CheckKey(VK_ESCAPE) = True Then 'если во время выбора нажали Esc
         If MsgBox("Повторить выбор, для техподполья", vbQuestion + vbYesNo, psVBProjectName) = vbNo Then
            bolVybor = True
         End If
      Else
         bolVybor = True
      End If
    Loop Until bolVybor = True
   End If
   
   'набор для элементов этажей
   If MsgBox("Выбрать элементы типовых этажей?", vbYesNo, psVBProjectName) = vbYes Then
      bolVybor = False
   
    Do
      selSetElevations.Clear
      varPt1 = ThisDrawing.Utility.GetPoint(, "Выбор объектов для спецификации этажей. Первая точка рамки:")
      varPt2 = ThisDrawing.Utility.GetCorner(varPt1, "Вторая точка рамки")
      ZoomWindow varPt1, varPt2
      selSetElevations.Select acSelectionSetCrossing, varPt1, varPt2, intFilterType, varFilterDate
      If CheckKey(VK_ESCAPE) Then 'если во время выбора нажали Esc
         If MsgBox("Повторить выбор, для типовых этажей", vbQuestion + vbYesNo, psVBProjectName) = vbYes Then
            bolVybor = False
         End If
      Else
         bolVybor = True
      End If
    Loop Until bolVybor = True
   End If
   
   'набор для элементов чердака
   If MsgBox("Выбрать элементы чердака?", vbYesNo, psVBProjectName) = vbYes Then
      bolVybor = False
    Do
      selSetRoof.Clear
      varPt1 = ThisDrawing.Utility.GetPoint(, "Выбор объектов для спецификации техподполья. Первая точка рамки:")
      varPt2 = ThisDrawing.Utility.GetCorner(varPt1, "Вторая точка рамки")
      ZoomWindow varPt1, varPt2
      selSetRoof.Select acSelectionSetCrossing, varPt1, varPt2, intFilterType, varFilterDate
      If CheckKey(VK_ESCAPE) Then 'если во время выбора нажали Esc
         If MsgBox("Повторить выбор, для чердака", vbQuestion + vbYesNo, psVBProjectName) = vbYes Then
            bolVybor = False
         End If
      Else
         bolVybor = True
      End If
    Loop Until bolVybor = True
   End If
   
   If MsgBox("Выбрано (блоков с атрибутами):" & vbCr & vbCr & _
      "Элементов техподполья = " & selSetDungeons.Count & vbCr & _
      "Элементов этажей = " & selSetElevations.Count & vbCr & _
      "Элементов чердака = " & selSetRoof.Count & vbCr & vbCr & _
      "Повторить пароцедуру выбора?", vbYesNo, psVBProjectName) = vbYes Then
      'повторяем процедуру
      MakeSelSets
   End If
   
   If selSetDungeons.Count = 0 And selSetElevations.Count = 0 And selSetRoof.Count = 0 Then
      MsgBox "Ничего не выбрано. Выход.", , psVBProjectName
      
      End
      
   End If

End Sub

Function CheckKey(lngKey As Long) As Boolean
  If GetAsyncKeyState(lngKey) Then
    CheckKey = True
  Else
    CheckKey = False
  End If
End Function

Private Sub ProvAllBlocksInDraw()
   'проверка блоков в наборе
   'атрибуты должны быть на своих слоях
   
   Dim selSetBlocks As AcadSelectionSet
   Dim objBlockRef As AcadBlockReference
   Dim objAtr As AcadAttributeReference
   Dim varAtr As Variant
   Dim bolYes(5) As Boolean
   Dim strSelSetName As String
   Dim i As Integer
   Dim intFilterType(1) As Integer
   Dim varFilterDate(1) As Variant
   
   strSelSetName = "Все_блоки"
   For Each selSetBlocks In ThisDrawing.SelectionSets
      If selSetBlocks.Name = strSelSetName Then
         selSetBlocks.Delete
         Exit For
      End If
   Next
   Set selSetBlocks = ThisDrawing.SelectionSets.Add(strSelSetName)
   
   intFilterType(0) = 0: intFilterType(1) = 66
   varFilterDate(0) = "insert": varFilterDate(1) = 1
   
   selSetBlocks.Select acSelectionSetAll, , , intFilterType, varFilterDate
   
   For Each objBlockRef In selSetBlocks
    For Each varAtr In objBlockRef.GetAttributes
      Set objAtr = varAtr
      Select Case objAtr.Layer
         Case "Att~Marka"
            bolYes(0) = True
         Case "Att~Massa"
            If Not IsNumeric(objAtr.TextString) Then
               GoTo Ошибка
            End If
            bolYes(1) = True
         Case "Att~Naimen"
'            objAtr.TextString = ProvNaimAndEdit(objAtr.TextString)'редактирование наименование
            bolYes(2) = True
         Case "Att~Obozn"
            bolYes(3) = True
         Case "Att~Material"
            bolYes(4) = True
         Case Else
            bolYes(5) = True
      End Select
    Next 'varAtr In objBlockRef.GetAttributes
      For i = 0 To 4
         If bolYes(i) = False Then
            GoTo Ошибка
         End If
      Next
      If bolYes(5) = True Then
         GoTo Ошибка
      End If
      For i = 0 To 5
         bolYes(i) = False
      Next
   Next 'objBlockRef In selSetBlocks
   
   selSetBlocks.Delete 'удаляем набор
   
Exit Sub

Ошибка:
   objBlockRef.Highlight True
   ZoomCenter objBlockRef.InsertionPoint, 10000
   MsgBox "В блоке - " & objBlockRef.Name & " - ошибка в атрибутах. Выход."
   End

End Sub
Private Function ProvNaimAndEdit(Naimen As String) As String
   
'   if
   
End Function


Private Sub MakeColOfTypeConstructions()
   'имеем наборы блоков с атриб, выбранные пользователем
   'составление массива с блоками
   
   Dim colBl As Collection
   Dim colNodes As Collection
   Dim strConect As String
   Dim strDBNodes As String
   Dim bolSpecNodes As Boolean
   Dim sSer As String
   
   If FormaShtamp.CheckBoxSpecNodes.Value = True Then
      bolSpecNodes = True
      sSer = FormaShtamp.ComboBoxNodesSer
      'подключение к базе
      'строка подключения
      If objConect.State = adStateOpen Then objConect.Close
         
         strDBNodes = strBDNodesFolder & "\Базы\dbNodes.mdb"
         strConect = strProvider & _
                  "Data Source=" & strDBNodes
         'подключение
         objConect.Mode = adModeRead
         objConect.Open strConect
   End If
   
   'создаем массивы typeConstructions и сортируем
   If ThisDrawing.SelectionSets.Item(strSelSetDungeons).Count <> 0 Then
      'создание коллекции блоков жб изделий и буферной коолекции блоков узлов
      Set colBl = FilterGB(strSelSetDungeons)
'      If bolSpecNodes = True Then
'         'создание коллекции объектов узлов из коллекции блоков узлов
'         If colNodeBlocksBuffer.Count <> 0 Then
'            Set colNodes = GetColNodes(colNodeBlocksBuffer, sSer)
'            'создание коллекции деталей техподполья
'            Set typeDetailDungeon = MakeColDetails(colNodes)
'            'сортировка деталей
'            SortyrArray typeDetailDungeon
'         End If
'      End If
      'создание массиво конструкциий из коллекции блоков
      Set typeDungeons = MakeColConstr(colBl)
      'сортировка конструкций
      SortyrArray typeDungeons
      bolArrayDungeon = True
   End If
   If ThisDrawing.SelectionSets.Item(strSelSetElevation).Count <> 0 Then
      'создание коллекции блоков жб изделий и буферной коолекции блоков узлов
      Set colBl = FilterGB(strSelSetElevation)
      'создание коллекции объектов узлов из коллекции блоков узлов
'      If bolSpecNodes = True Then
'         If colNodeBlocksBuffer.Count <> 0 Then
'            Set colNodes = GetColNodes(colNodeBlocksBuffer, sSer)
'            'создание коллекции деталей техподполья
'            Set typeDetailElev = MakeColDetails(colNodes)
'            'сортировка деталей
'            SortyrArray typeDetailElev
'         End If
'      End If
      'создание массиво конструкциий из коллекции блоков
      Set typeElevs = MakeColConstr(colBl)
      SortyrArray typeElevs
      bolArrayElev = True
   End If
   If ThisDrawing.SelectionSets.Item(strSelSetRoof).Count <> 0 Then
      'создание коллекции блоков жб изделий и буферной коолекции блоков узлов
      Set colBl = FilterGB(strSelSetRoof)
      'создание коллекции объектов узлов из коллекции блоков узлов
'      If bolSpecNodes = True Then
'         If colNodeBlocksBuffer.Count <> 0 Then
'            Set colNodes = GetColNodes(colNodeBlocksBuffer, sSer)
'            'создание коллекции деталей техподполья
'            Set typeDetailDungeon = MakeColDetails(colNodes)
'            'сортировка деталей
'            SortyrArray typeDetailDungeon
'         End If
'      End If
      'создание массиво конструкциий из коллекции блоков
      Set typeRoofs = MakeColConstr(colBl)
      SortyrArray typeRoofs
      bolArrayRoof = True
   End If
   
   
   'создание коллекции объектов узлов из коллекции блоков узлов
      If bolSpecNodes = True Then
         If colNodeBlocksBuffer.Count <> 0 Then
            Set colNodes = GetColNodes(colNodeBlocksBuffer, sSer)
            'создание коллекции деталей техподполья
            Set typeDetailDungeon = MakeColDetails(colNodes)
            'сортировка деталей
            SortyrArray typeDetailDungeon
         End If
      End If
   
   
   'закрываем связь с базой узлов
   If objConect.State = adStateOpen Then objConect.Close
   
End Sub
Private Function MakeColConstr(colBl As Collection) As Collection
   'создание массива изделий
   
   Dim objBlock As AcadBlockReference
   Dim selSet As AcadSelectionSet
   Dim strBlockName As String
   Dim strPromt As String
   Dim strAtrTagForPromt As String
   Dim bolYesNo As Boolean
   Dim intNomer As Integer
   Dim i As Integer
   Dim intPosAtr(2) As Integer
   Dim varAtr As Variant
   Dim objAtr As AcadAttributeReference
   Dim typeConstr As Constructs

'   Set selSet = ThisDrawing.SelectionSets.Item(SelSetName)

   Set MakeColConstr = New Collection
   
   For Each objBlock In colBl
      strBlockName = objBlock.Name
      On Error Resume Next
      Set typeConstr = MakeColConstr.Item(strBlockName)
      On Error GoTo 0
      If typeConstr Is Nothing Then
         'добавляем описание блока в массив
         'получаем атрибуты блока
         Set typeConstr = New Constructs
         
         typeConstr.Kolvo = 1
         For Each varAtr In objBlock.GetAttributes
            Set objAtr = varAtr
            Select Case objAtr.Layer
               Case "Att~Marka"
                  typeConstr.Name = objAtr.TextString
               Case "Att~Massa"
                  typeConstr.Massa = Val(objAtr.TextString)
               Case "Att~Naimen"
                  typeConstr.Naimen = ReturnNaimenForSpec(objAtr.TextString)
               Case "Att~Obozn"
                  typeConstr.Obozn = objAtr.TextString
            End Select
         Next
         MakeColConstr.Add typeConstr, typeConstr.Name
      Else
         typeConstr.Kolvo = typeConstr.Kolvo + 1
      End If
      Set typeConstr = Nothing
   Next

End Function
Private Function ReturnNaimenForSpec(Naimen As String) As String
   'возвращаем наименование изделия для спецификации
   
   Dim bOther As Boolean
   
   If LCase(Naimen) Like ("нар*стен*панель") Then
      ReturnNaimenForSpec = "1Нар. стен. панель"
   ElseIf LCase(Naimen) Like ("внутр*стен*панель") Then
      ReturnNaimenForSpec = "2Внутр. стен. панель"
   ElseIf LCase(Naimen) Like ("плита*перекрытия") Then
      ReturnNaimenForSpec = "3Плита перекрытия"
   ElseIf LCase(Naimen) Like ("плита*покрытия") Then
      ReturnNaimenForSpec = "4Плита покрытия"
   ElseIf LCase(Naimen) Like ("блок*шахты*лифта") Then
      ReturnNaimenForSpec = "Блок шахты лифта"
   ElseIf LCase(Naimen) Like ("стенка*лоджии") Then
      ReturnNaimenForSpec = "Стенка лоджии"
   ElseIf LCase(Naimen) Like ("лестничный*марш") Then
      ReturnNaimenForSpec = "Лестничный марш"
   ElseIf LCase(Naimen) Like ("лестничный*марш") Then
      ReturnNaimenForSpec = "Лестничный марш"
   ElseIf LCase(Naimen) Like ("оголовок*вентблока") Then
      ReturnNaimenForSpec = "Оголовок вентблока"
   ElseIf LCase(Naimen) Like ("опора*лотка") Then
      ReturnNaimenForSpec = "Опора лотка"
   ElseIf LCase(Naimen) Like ("лестничная*площадка") Then
      ReturnNaimenForSpec = "Лестничная площадка"
   ElseIf LCase(Naimen) Like ("плита*лоджии") Then
      ReturnNaimenForSpec = "Плита лоджии"
   ElseIf LCase(Naimen) Like ("козырек*входа") Then
      ReturnNaimenForSpec = "Козырек входа"
   ElseIf LCase(Naimen) Like ("экран*входа") Then
      ReturnNaimenForSpec = "Экран входа"
   ElseIf LCase(Naimen) Like ("лоток*крыши") Then
      ReturnNaimenForSpec = "Лоток крыши"
   Else
      bOther = True
   End If
   
   If bOther = True Then
      'для любых других наименований заменяем "_" на " "
      Naimen = VBA.Replace(Naimen, "_", " ")
      ReturnNaimenForSpec = Naimen
   End If
   
'   ReturnNaimenForSpec = Replace(Naimen, "_", " ")
   
End Function
Private Function GetPromtAtr(BlockName As String, Promt As String) As Integer
   'идентификация атрибутов в varAtr по подсказке
      
   Dim objBlock As AcadBlock
   Dim objAcadItem As AcadObject
   Dim objAtr As AcadAttribute
   
   Set objBlock = ThisDrawing.Blocks.Item(BlockName)
   
   For Each objAcadItem In objBlock
      If objAcadItem.ObjectName = "AcDbAttributeDifinition" Then
         Set objAtr = objAcadItem
         If LCase(objAtr.PromptString) = "масса" Then
         
         End If
      End If
   Next
   
End Function

Private Sub SortyrArray(ByRef colConstr As Collection)
   'сортировка массивов typeConstructions
   
   Dim typeConstr As Constructs
   Dim intCount As Integer
   Dim j As Integer
   Dim i As Integer
   Dim strNaimen As String
   
   intCount = colConstr.Count
   For i = 1 To intCount - 1
      For j = 1 To intCount - i
         'сортируем наименования
         If StrComp(colConstr.Item(j).Naimen, colConstr.Item(j + 1).Naimen, vbTextCompare) = 1 Then
            Set typeConstr = colConstr.Item(j)
            colConstr.Remove j
            colConstr.Add typeConstr, typeConstr.Name, , j
         'если наименования равны то сортируем по имени
         ElseIf StrComp(colConstr.Item(j).Naimen, colConstr.Item(j + 1).Naimen, vbTextCompare) = 0 Then
            If StrComp(colConstr.Item(j).Name, colConstr.Item(j + 1).Name, vbTextCompare) = 1 Then
               Set typeConstr = colConstr.Item(j)
               colConstr.Remove j
               colConstr.Add typeConstr, typeConstr.Name, , j
            End If
         End If
      Next
   Next
   
   'восстанавливаем наименования с нмерам в начале
   For i = 1 To intCount
      strNaimen = colConstr.Item(i).Naimen
      If strNaimen Like ("1Нар. стен. панель") Then
         strNaimen = "Нар. стен. панель"
      ElseIf strNaimen Like ("2Внутр. стен. панель") Then
         strNaimen = "Внутр. стен. панель"
      ElseIf strNaimen Like ("3Плита перекрытия") Then
         strNaimen = "Плита перекрытия"
      ElseIf strNaimen Like ("4Плита покрытия") Then
         strNaimen = "Плита покрытия"
      End If
      colConstr.Item(i).Naimen = strNaimen
   Next
   
End Sub

Private Sub MakeSpecif()
   'создание файла со спецификацией в корне с текущим файлом
   
'   Dim strMacroPath As String
   Dim strMacroFolder As String
   Dim strZagTableFullPath As String
   Dim strThisDrawPath As String
   
   Dim strTableFileName As String
   Dim strThisDrawName As String
   Dim strShifr As String
   Dim intValue As Integer
   
   
'********* создаем файлы для специфиукации ***********************
   
   'определяем путь к кореню запущенного макроса
'   strMacroPath = AutoCAD.Application.VBE.activeVBProject.FileName
'   strMacroPath = AutoCAD.Application.VBE.vbprojects.Item("SpecKonstr").FileName
'   intValue = InStrRev(strMacroPath, "\")
'   strMacroFolder = Left(strMacroPath, intValue)
   strMacroFolder = Functions.GetMacroFolder("SpecKonstr")
   strZagTableFullPath = strMacroFolder & "\Таблицы\Таблицы.dwg"
'   strMacroPath = AutoCAD.Application.VBE.MainWindow.Caption
   'проверяем есть ли файл с заготовкой таблицы
   If Dir(strZagTableFullPath) = "" Then
      MsgBox "Файл с шаблоном таблицы не найден!" & vbCrLf _
            & "В корне макроса должна быть папка Таблицы с файлом Таблицы.dwg" & vbCrLf _
            & "Выход."
      End
   End If
   'определяем путь к корню текущего чертежа
   strThisDrawPath = ThisDrawing.Path
   strThisDrawName = ThisDrawing.Name
'   If strThisDrawName Like ("Монт.схемы*") Then
'      intValue = InStr(strThisDrawName, ")") - 11
'      strShifr = Mid(strThisDrawName, 12, intValue)
'   End If
   strTableFileName = "Спец.ж.б.изд. " & FormaShtamp.TextBoxShifr & " (" & FormaShtamp.TextBoxNaimen & ")"
   strTableFileName = Replace(strTableFileName, Chr(34), "")
   strTableFullPath = strThisDrawPath & "\" & strTableFileName & ".dwg"
   'проверяем есть ли такой файл
   If Dir(strTableFullPath) <> "" Then
      'если он открыт
      FormaRename.cmbReplace.Enabled = True
      Dim objDocTemp  As AcadDocument
      For Each objDocTemp In Documents
         If objDocTemp.FullName = strTableFullPath Then
            FormaRename.cmbReplace.Enabled = False
            Exit For
         End If
      Next
      FormaRename.TextBoxFileName = strTableFileName
      FormaRename.LabelFilePath = strTableFullPath
      FormaRename.Show
      If FormaRename.bolReplace = False Then 'изменяем имя
         strTableFileName = FormaRename.TextBoxFileName
         strTableFullPath = strThisDrawPath & "\" & strTableFileName & ".dwg"
      Else
         Kill strTableFullPath
      End If
   End If
      
   'копируем заготовку для таблицы в корень текущего чертежа, предварительно проверяем наличие файла
   FileCopy strZagTableFullPath, strTableFullPath
   
'********* Конец создания файла для специфиукации ***********************

'********* Заполняем таблицы *******************************************
         
   'открываем файл с таблицей
'   AcadApplication.Documents.Open strTableFullPath
      
   objDoc.Open strTableFullPath
   Set objMS = objDoc.ModelSpace
   
   'внедряем определения блоков штампов из "\\Sgpsrv2\СПД\Конструкторы\Макросы\Шифры\Штампы.dwg"
   If Functions.AddBlocksFromDWG(strStampsDwgFullPath) = False Then
      'вставить блоки не удалось
   End If
   
   'начинаем с typeDungeons
   If bolArrayDungeon = True Then  'если есть массв эементов техподполья
      ZapTable typeDungeons, DrawingNaimen.Dungeon, TypeConstrEnum.GB   'заполняем таблицу данными из массива typeDungeons
   End If
   If bolArrayElev = True Then   'если есть массв эементов этажей
      ZapTable typeElevs, DrawingNaimen.Elev, TypeConstrEnum.GB   'заполняем таблицу данными из массива typeConstructs
   End If
   If bolArrayRoof = True Then   'если есть массв эементов чердака
      ZapTable typeRoofs, DrawingNaimen.Roof, TypeConstrEnum.GB  'заполняем таблицу данными из массива typeConstructs
   End If
   
   If FormaShtamp.CheckBoxSpecNodes.Value = True Then
      'заполняем спецификации узлов
      If typeDetailDungeon.Count <> 0 Then 'если есть массв эементов техподполья
         ZapTable typeDetailDungeon, DrawingNaimen.Nodes, TypeConstrEnum.Node 'заполняем таблицу данными из массива typeDetailDungeon
      End If
      If typeDetailElev.Count <> 0 Then  'если есть массв эементов этажей
         ZapTable typeDetailElev, DrawingNaimen.DetElev, TypeConstrEnum.Node 'заполняем таблицу данными из массива typeDetailElev
      End If
      If typeDetailRoof.Count <> 0 Then  'если есть массв эементов чердака
         ZapTable typeDetailRoof, DrawingNaimen.DetRoof, TypeConstrEnum.Node  'заполняем таблицу данными из массива typeDetailRoof
      End If
   End If
   
   'Добавление таблицы со списком наименований спецификаций для Архитекторов.
   TableForArchitectors
   
   'сохраняем и закрываем файл
   objDoc.SaveAs strTableFullPath
   
End Sub
Private Sub ZapTable(colConstr As Collection, DrawingNaimen As Integer, intTypeConstr As Integer)
   'вставка и заполнение листов спецификации техподполья
   
   Dim objTable As AcadTable
   Dim intRow As Integer
   Dim intRowsTable As Integer
   Dim i As Integer
   Dim intUbound As Integer
   
   'вставляем лист
   intUbound = colConstr.Count
   If intUbound > 56 Then
      'вставляем лист А2
      'если изделий больше 136,т.е. больше чем может уместиться на одном листе А2
      'то вписываем в наименование листа "( начало)"
      If intUbound > 136 Then
         Set objTable = DobLista(Format.A2, DrawingNaimen, " (начало)")
      Else
         Set objTable = DobLista(Format.A2, DrawingNaimen)
      End If
   Else
      'вставляем лист А3
      Set objTable = DobLista(Format.A3, DrawingNaimen)
   End If
   objTable.RegenerateTableSuppressed = True
   
   intRowsTable = objTable.Rows
   For i = 1 To colConstr.Count
      intRow = intRow + 1 'индекс с 0,начинаем заполнять таблу со второй строчки, первая - заголовок
      
      'проверяем хватает ли строк в таблице
      If intRow = intRowsTable Then 'добавляем новый лист
                  
         objTable.RegenerateTableSuppressed = False
         intUbound = colConstr.Count + 1 - i
         If intUbound > 56 Then 'если оставшихся изделий больше чем строк в таблице А3 листа
            'проверяем это будет последний лист или нет
            If intUbound > 136 Then
               Set objTable = DobLista(Format.A2, DrawingNaimen, " (продолжение)")
            Else
               Set objTable = DobLista(Format.A2, DrawingNaimen, " (окончание)")
            End If
         Else
            Set objTable = DobLista(Format.A3, DrawingNaimen, " (окончание)")
         End If
         objTable.RegenerateTableSuppressed = True
         intRow = 1
         intRowsTable = objTable.Rows
      End If
      
      objTable.SetText intRow, 1, colConstr.Item(i).Obozn
      objTable.SetText intRow, 2, colConstr.Item(i).Naimen
      objTable.SetText intRow, 3, colConstr.Item(i).Name
      objTable.SetText intRow, 4, colConstr.Item(i).Kolvo
      If intTypeConstr = TypeConstrEnum.GB Then
         objTable.SetText intRow, 5, FormatNumber(colConstr.Item(i).Massa, 0)
      Else
         objTable.SetText intRow, 5, FormatNumber(colConstr.Item(i).Massa, 2)
      End If
      
'      'временно
'      objTable.SetText intRow, 0, i + 1
      
   Next
   objTable.RegenerateTableSuppressed = False
'   'временно для проверки вставляем колличество элементов в массиве
'   intRow = intRow + 1 'заносить будем в след строку в таблице
'   If intRow = intRowsTable Then  'проблема нет пустых строчек
'      objTable.InsertRows intRow, 8, 1
'   End If
'   objTable.SetText intRow, 1, "Кол.эл. в массиве"
'   objTable.SetText intRow, 4, UBound(typeConstructs) + 1
   
   'удалим пустые ячейки в таблице
   If intRowsTable - (intRow + 1) > 0 Then
      objTable.DeleteRows intRow + 1, intRowsTable - intRow 'олжна остаться одна пуста строчка
      'устанавливаем толщину нижней границы последней строке в 3 столбце
      objTable.SetCellGridLineWeight intRow, 3, AcCellEdgeMask.acBottomMask, AcLineWeight.acLnWt050
   End If
   
End Sub
Private Function DobLista(Format As Integer, intDrawingNaimen As Integer, Optional strNext As String) As AcadTable
   'вставка листа с учетом текущей точки вставки последнего листа
   
   Dim objBlockRamka As AcadBlockReference
   Dim objBlockTable As AcadBlockReference
   Dim selSetList As AcadSelectionSet
   Dim objAcad As AcadObject
   Dim objTable As AcadTable
   Dim strSelSet As String
   Dim dPt2(2) As Double
   Dim bolYes As Boolean
   Dim varAtr As Variant
   Dim objAtr() As AcadAttributeReference
   Dim strFormat As String
   Dim strDrawNaimen As String
   Dim aobjEntity As AcadEntity
   Dim varObjects As Variant
   Dim i As Integer
   Dim dPtForSel1(2) As Double
   Dim dPtForSel2(2) As Double
   
   
   If Format = 1 Then
      strFormat = "ЛистА2"
   ElseIf Format = 2 Then
      strFormat = "ЛистА3"
   ElseIf Format = 3 Then
      strFormat = "ЛистА4"
   End If
   
   Select Case intDrawingNaimen
      Case DrawingNaimen.Dungeon
         strDrawNaimen = "Спецификация ж.б.изделий техподполья"
      Case DrawingNaimen.Elev
         strDrawNaimen = "Спецификация ж.б.изделий " & FormaShtamp.TextBoxFloor & " этажей"
      Case DrawingNaimen.Roof
         strDrawNaimen = "Спецификация ж.б.изделий чердака и покрытия"
      Case DrawingNaimen.DetDungeon
         strDrawNaimen = "Спецификация соединительных изделий чердака и покрытия"
      Case DrawingNaimen.DetElev
         strDrawNaimen = "Спецификация соединительных изделий " & FormaShtamp.TextBoxFloor & " этажей"
      Case DrawingNaimen.DetRoof
         strDrawNaimen = "Спецификация соединительных изделий техподполья"
      Case DrawingNaimen.Nodes
         strDrawNaimen = "Спецификация соединительных изделий"
   End Select
   
   intNomerDobLista = intNomerDobLista + 1
   If intNomerDobLista > 1 Then 'определяем точку вставки листиа
      If strFormat = "ЛистА2" Then
         dPtInsertTable(1) = dPtInsertTable(1) - 420 - 20
         'точка противоположного угла
         dPt2(0) = dPtInsertTable(0) + 594
         dPt2(1) = dPtInsertTable(1) + 420
      ElseIf strFormat = "ЛистА3" Then
         dPtInsertTable(1) = dPtInsertTable(1) - 297 - 20
         'точка противоположного угла
         dPt2(0) = dPtInsertTable(0) + 420
         dPt2(1) = dPtInsertTable(1) + 297
      ElseIf strFormat = "ЛистА4" Then
         dPtInsertTable(1) = dPtInsertTable(1) - 297 - 20
         'точка противоположного угла
         dPt2(0) = dPtInsertTable(0) + 210
         dPt2(1) = dPtInsertTable(1) + 297
      End If
      dPtForSel1(0) = dPtInsertTable(0) - 5
      dPtForSel1(1) = dPtInsertTable(1) - 5
      dPtForSel2(0) = dPt2(0) + 5
      dPtForSel2(1) = dPt2(1) + 5
   Else
      If strFormat = "ЛистА2" Then
         dPt2(0) = 594
         dPt2(1) = 420
      ElseIf strFormat = "ЛистА3" Then
         dPt2(0) = 420
         dPt2(1) = 297
      ElseIf strFormat = "ЛистА4" Then
         dPt2(0) = 210
         dPt2(1) = 297
      End If
      dPtForSel1(0) = -5
      dPtForSel1(1) = -5
      dPtForSel2(0) = dPt2(0)
      dPtForSel2(1) = dPt2(1)
   End If
   
'   strSelSet = "Лист"
'   For Each selSetList In objMS.SelectionSets
'      If selSetList.Name = strSelSet Then
'         selSetList.Delete
'         Exit For
'      End If
'   Next
'   Set selSetList = ThisDrawing.SelectionSets.Add(strSelSet)
   
   Set objBlockTable = objMS.InsertBlock(dPtInsertTable, strFormat, 1, 1, 1, 0)
   varObjects = objBlockTable.Explode 'разбиваем блок
   objBlockTable.Delete
'   ZoomExtents
   
'   'выбираем лист
'   selSetList.Select acSelectionSetWindow, dPtForSel1, dPtForSel2
'
'   If selSetList.Count <> 2 Then
'      MsgBox "В наборе не два объекта!? Выход."
'      End
'   End If
   bolYes = False
   For i = 0 To UBound(varObjects)
      If TypeOf varObjects(i) Is AcadBlockReference Then
         Set objBlockRamka = varObjects(i) 'штамп чертежа
         bolYes = True
      ElseIf TypeOf varObjects(i) Is AcadTable Then
         Set objTable = varObjects(i) 'таблица
         bolYes = True
      End If
   Next
   If bolYes = False Then
      MsgBox "В блоке листа не найдена таблица или рамка!? Выход."
      End
   End If
   
   Dim strNaimen As String
   
   Dim ad As AcadAttribute
   Dim ar As AcadAttributeReference
   
   'заполняем атрибуты штампа из формы
   varAtr = objBlockRamka.GetAttributes
   varAtr(0).TextString = FormaShtamp.TextBoxShifr
   varAtr(1).TextString = FormaShtamp.TextBoxZakaz
   varAtr(2).TextString = FormaShtamp.TextBoxAdress
   varAtr(3).TextString = FormaShtamp.TextBoxNomerDoma
   If FormaShtamp.TextBoxNaimen <> "" Then
      strNaimen = strDrawNaimen & " " & FormaShtamp.TextBoxNaimen
   Else
      'пусто, т.е. для всего дома
      strNaimen = strDrawNaimen
   End If
   If strNext <> "" Then
      strNaimen = strNaimen & strNext
   End If
   varAtr(4).TextString = strNaimen
   varAtr(5).TextString = FormaShtamp.TextBoxPost1
   varAtr(6).TextString = FormaShtamp.TextBoxFam1
   varAtr(7).TextString = FormaShtamp.TextBoxPost2
   varAtr(8).TextString = FormaShtamp.TextBoxFam2
   varAtr(9).TextString = FormaShtamp.TextBoxPost3
   varAtr(10).TextString = FormaShtamp.TextBoxFam3
   varAtr(11).TextString = FormaShtamp.TextBoxPost4
   varAtr(12).TextString = FormaShtamp.TextBoxFam4
   varAtr(13).TextString = FormaShtamp.TextBoxPost5
   varAtr(14).TextString = FormaShtamp.TextBoxFam5
   If (Len(FormaShtamp.TextBoxFam5) > 10) Then
      varAtr(14).ScaleFactor = 0.8
   End If
   varAtr(19).TextString = FormaShtamp.TextBoxStage
   
   Erase dPt2
   Set objBlockRamka = Nothing
'   selSetList.Clear
   
   Set DobLista = objTable
   
End Function


'Private Sub AllProverks()
'   'все проверки блоков, зеркальность, наложение, видимого атрибута
'
''   'нужно проверить все три набора
''   If ThisDrawing.SelectionSets.Item(strSelSetDungeons).Count <> 0 Then
''      ProvSelSet strSelSetDungeons
''   End If
''   If ThisDrawing.SelectionSets.Item(strSelSetElevation).Count <> 0 Then
''      ProvSelSet strSelSetElevation
''      End If
''   If ThisDrawing.SelectionSets.Item(strSelSetRoof).Count <> 0 Then
''      ProvSelSet strSelSetRoof
''   End If
'
'End Sub
'Private Sub ProvSelSet(strSelSet As String)
Private Sub AllProverks()
   'проверка набора на зеркальность, наложение, имени и атрибута
   
   'зона наложения
   Const intRadNalog As Integer = 100
   
   Dim objBlockRef As AcadBlockReference
   Dim objBlockRef2 As AcadBlockReference
   Dim objAttr As AcadAttributeReference
   Dim objSelSet As AcadSelectionSet
   Dim objSelSet2 As AcadSelectionSet
   Dim Cros1(2) As Double
   Dim Cros2(2) As Double
   Dim intFilterType(2) As Integer
   Dim varFilterDate(2) As Variant
   Dim vMinPt1 As Variant
   Dim vMaxPt1 As Variant
   Dim vMinPt2 As Variant
   Dim vMaxPt2 As Variant
   Dim varAttributes As Variant
   Dim intOtvet As Integer
   
'   Set objSelSet = ThisDrawing.SelectionSets.Item(strSelSet)
   Set objSelSet = Functions.GetSelSet("Проверка")
   
   'фильтр блоков  с атрибутом
   intFilterType(0) = 0: intFilterType(1) = 66: intFilterType(2) = 66
   varFilterDate(0) = "insert": varFilterDate(1) = 1: varFilterDate(2) = 1
   
   objSelSet.Select acSelectionSetAll, , , intFilterType, varFilterDate
   
   ZoomAll
   
   'создаем вспомогательный набор
   Set objSelSet2 = Functions.GetSelSet("Вокруг блока")
   
   'перебор всех объектов набора
   For Each objBlockRef In objSelSet
      
      'проверка зеркальности
      If Sgn(objBlockRef.XScaleFactor) = -1 Or Sgn(objBlockRef.YScaleFactor) = -1 Then 'если отрицательное число, значит отзеркален
         'добавляем блок в коллекцию зеркальных блоков
         colBlocksZerkal.Add objBlockRef
         bolProverka = True
      End If 'если отрицательное число
      
      'проверка наложения
      'получаем границы первого блока
      objBlockRef.GetBoundingBox vMinPt1, vMaxPt1
      'задаем точки выбора для рамки вокруг блока
      Cros1(0) = objBlockRef.InsertionPoint(0) - 7000: Cros1(1) = objBlockRef.InsertionPoint(1) - 7000: Cros1(2) = 0
      Cros2(0) = objBlockRef.InsertionPoint(0) + 7000: Cros2(1) = objBlockRef.InsertionPoint(1) + 7000: Cros2(2) = 0
      'фильтр блока по имени с атрибутом
      intFilterType(0) = 0: intFilterType(1) = 2: intFilterType(2) = 66
      varFilterDate(0) = "insert": varFilterDate(1) = objBlockRef.Name: varFilterDate(2) = 1
      'выбираем
      objSelSet2.Select acSelectionSetCrossing, Cros1, Cros2, intFilterType, varFilterDate
      'перебираем эти блоки вокруг блока
      For Each objBlockRef2 In objSelSet2 'перебор всех объектов набора
         If Not objBlockRef2 Is objBlockRef Then  'проверяем что бы это не было objBlockRef is objBlockRef2
            objBlockRef2.GetBoundingBox vMinPt2, vMaxPt2
            If ProvBoundingBox(vMinPt1, vMinPt2, vMaxPt1, vMaxPt2, intRadNalog) = True Then
               'добавляем блок в коллекцию дублирующихся блоков
               colBlocksNalogenie.Add objBlockRef
               bolProverka = True
            End If
         End If
      Next
      objSelSet2.Clear
      
      'проверка имени блока и атрибута марки
      For Each varAttributes In objBlockRef.GetAttributes
         Set objAttr = varAttributes
         If LCase(objAttr.Layer) = "att~marka" Then 'атрибут марки должен быть на слое Att~Marka
            'если имя блока не равно имени атрибута
            If StrComp(objAttr.TextString, objBlockRef.Name, vbTextCompare) <> 0 Then
               colBlocksErrName.Add objBlockRef
               bolProverka = True
'               Exit For 'выходим из перебора атрибутов
            End If
         End If
         'проверка неопределенных блоков как жб изделия
         'т.е. материал<>жб
         If LCase(objAttr.Layer) = "att~material" Then
            If LCase(objAttr.TextString) <> "железобетон" Then
               'значит это фиг знает что
               colBlockBrack.Add objBlockRef
               bolProverka = True
            End If
         End If
      Next
      
   Next 'objBlockRef In objSelSet
   
End Sub


Private Function ProvBlockIzdOnFreezeLayers() As Boolean
   'проверяем есть ли блоки изделий на замороженных слоях
   'true - продолжить программу
   'False - закончить программу
   
   Dim objLayer As AcadLayer
   Dim objSelSetFreeze As AcadSelectionSet
   Dim objBlockRef As AcadBlockReference
   Dim objAtt As AcadAttributeReference
   Dim intFilterType(2) As Integer
   Dim varFilterDate(2) As Variant
   Dim varAtt As Variant
   Dim intOtvet As Integer
   
   Dim aobjBlocksTemp() As AcadBlockReference
   Dim bolFreezeBlocks As Boolean
   Dim i As Integer
   Dim j As Integer
   
   'проверка, если уже есть такой набор в чертее, удаляем его
   Set objSelSetFreeze = Functions.GetSelSet("ЗамороженныеБлокиИзделий")
   
   'задаем фильтр блоков с атрибутами на заданном слое
   intFilterType(0) = 0: intFilterType(1) = 66: intFilterType(2) = 8
   varFilterDate(0) = "Insert": varFilterDate(1) = 1
   
   'находим заморженные слои и выбираем все блоки на этом слое
   For Each objLayer In ThisDrawing.Layers
      If objLayer.Freeze = True Then
'         objLayer.Freeze = False
         varFilterDate(2) = objLayer.Name
         'выбираем все блоки на этом слое
         objSelSetFreeze.Clear
         objSelSetFreeze.Select acSelectionSetAll, , , intFilterType, varFilterDate
         'ищем блоки изделий в наборе
         i = 0
         For Each objBlockRef In objSelSetFreeze
            For Each varAtt In objBlockRef.GetAttributes
               Set objAtt = varAtt
               If objAtt.Layer = "Att~Material" And StrComp(objAtt.TextString, "Железобетон", vbTextCompare) = 0 Then
                  'значит это блок изделия, на замороженном слое (т.е. его не видно на экране)
                  ReDim Preserve aobjBlocksTemp(i)
                  Set aobjBlocksTemp(i) = objBlockRef 'записываем блок жб изделия на этом замороженном слое
                  i = i + 1
               End If
            Next
         Next 'objBlockRef In objSelSetFreeze
         'записываем блоки в массив замороженных блоков и слоев
            If i > 0 Then 'если найден хоть один блок на этом замороженном слое
               ReDim Preserve FreezeBlocks(j)
               FreezeBlocks(j).LayerName = objLayer.Name
               Set FreezeBlocks(j).colBlocks = New Collection
               For i = 0 To UBound(aobjBlocksTemp)
                  FreezeBlocks(j).colBlocks.Add aobjBlocksTemp(i), CStr(i)
               Next
               FreezeBlocks(j).IsBlocks = True
               bolFreezeBlocks = True
               j = j + 1 'счетчик замороженных слоев с блоками жб изделий
            End If
      End If
   Next
   
   'выводим форму со списками замороженных слоев и блоков на них
   If bolFreezeBlocks = True Then
      'форма выводится в модальном режиме, с возможностью продолжения, при этом все слои обратно заморозятся,
      'и возможность завершения программы, м переключением этой формы в немодальный режим, для подробного просмотрка блоков
      ThisDrawing.Regen acActiveViewport
      FormaFreezeBlock.Show
      If bolFreezeOk = True Then
         'продолжаем программу
         ProvBlockIzdOnFreezeLayers = True
      Else
         'заканчиваем программу
         ProvBlockIzdOnFreezeLayers = False
      End If
   Else
      ProvBlockIzdOnFreezeLayers = True
   End If
   
End Function

Private Function ProvBoundingBox(MinPt1 As Variant, MinPt2 As Variant, MaxPt1 As Variant, MaxPt2 As Variant, Dopusk As Integer) As Boolean
   'проверка наложенитя точек
   'наложение считается совпадение (в допусках) обоих точек BoundingBox
   'True - наложение
   
   'проверяем первую точку
   If MinPt2(0) < MinPt1(0) + Dopusk And MinPt2(0) > MinPt1(0) - Dopusk And _
       MinPt2(1) < MinPt1(1) + Dopusk And MinPt2(1) > MinPt1(1) - Dopusk Then
       'проверяем вторую точку
      If MaxPt2(0) < MaxPt1(0) + Dopusk And MaxPt2(0) > MaxPt1(0) - Dopusk And _
          MaxPt2(1) < MaxPt1(1) + Dopusk And MaxPt2(1) > MaxPt1(1) - Dopusk Then
          'значит точки лежат в пределах наложения, т.е. блоки накладываются
          ProvBoundingBox = True
      Else
         ProvBoundingBox = False
      End If
   Else
      ProvBoundingBox = False
   End If
   
End Function

Private Sub FilterGBinSelSets()
   'оставляем в наборах только блоки жб изделий, блоки узлров заносим в коллекцию узлов
   
   If ThisDrawing.SelectionSets.Item(strSelSetDungeons).Count <> 0 Then
      FilterGB strSelSetDungeons
   End If
   If ThisDrawing.SelectionSets.Item(strSelSetElevation).Count <> 0 Then
      FilterGB strSelSetElevation
   End If
   If ThisDrawing.SelectionSets.Item(strSelSetRoof).Count <> 0 Then
      FilterGB strSelSetRoof
   End If
   
End Sub

Private Function FilterGB(strSelSetName As String) As Collection
   'оставляем в наборе только блоки жб изделий, блоки узлров заносим в коллекцию узлов
   
   Dim objSelSet As AcadSelectionSet
   Dim objBlRef As AcadBlockReference
   Dim bolYes As Boolean
   Dim varAtr As Variant
   
   'Set colNodeBlocksBuffer = Nothing
   
   Set FilterGB = New Collection
   
   Set objSelSet = ThisDrawing.SelectionSets.Item(strSelSetName)
   
   For Each objBlRef In objSelSet
      If objBlRef.Name = "Узел" Then
         'все блоки Узлов добавляем в коллекцию
         colNodeBlocksBuffer.Add objBlRef
      Else
         'проверяем атрибут материал=железобетон
         bolYes = False
         For Each varAtr In objBlRef.GetAttributes
            If LCase(varAtr.Layer) = "att~material" Then
               If LCase(varAtr.TextString) = "железобетон" Then
                  FilterGB.Add objBlRef
                  bolYes = True
                  Exit For
               End If
            End If
         Next
         If bolYes = False Then
            'заносим блок в коллекцию забракованных блоков
            colBlockBrack.Add objBlRef
         End If
      End If
   Next
   
End Function

Private Function ProvBaseNodeState() As String
   'проверка статуса базы узлов
   'при редактировании базы появляется файл dbNodes.ldb рядом с осеовным файлом базы, его и нужно посмотреть
   'ИмяПользователя - если база редактируется
   '"" - если нет
   
   Dim strLBDNodesFullPath As String
   Dim strMacroFolder As String
   Dim strValue As String
   Dim intValue As Integer
   
   'путь к этому проекту: \\Sgpsrv2\СПД\Конструкторы\Макросы\SpecKonstr.dvb
   strMacroFolder = Functions.GetMacroFolder(psVBProjectName)
   'надо получить: \\Sgpsrv2\СПД\Конструкторы\Макросы\dbNodes.ldb
   intValue = InStrRev(strMacroFolder, "\")
   strValue = Left(strMacroFolder, intValue) 'без имени SpecKonstr\SpecKonstr.dvb, т.е \\Sgpsrv2\СПД\Конструкторы\Макросы\
'   strBDNodesFolder = strValue ' & "BaseNodes"
   strBDNodesFolder = strMacroFolder
   strLBDNodesFullPath = strBDNodesFolder & "\Базы\dbNodes.ldb"
   'проверяем есть ли такой файл
   If Dir(strLBDNodesFullPath) = "" Then
      'нет такого файла
      ProvBaseNodeState = ""
   Else
      'нужно его открыть и прочитать первую строчку
      Open strLBDNodesFullPath For Input As #1
        Input #1, strValue
      Close #1
      If strValue <> "" Then
         'нужно выцепить из строчки имя пользователя
         ProvBaseNodeState = strValue
      Else
         'тогда не знаю что
         ProvBaseNodeState = strValue
      End If
   End If
   
End Function

Private Function GetColNodes(colBlNode As Collection, sSer As String) As Collection
   'обработка коллекции блоков узлов и создание коолекции объектов узлов, по данным из базы
   'на выходе получаем коллекцию объектоа узлов colNodes
   
   Dim objCommand As New ADODB.Command
   Dim recNodes As New ADODB.Recordset
   Dim recNodeDetails As New ADODB.Recordset
   Dim strBaseTable As String
   Dim objBlNode As AcadBlockReference
   Dim objNode As clNode
   Dim objDetail As Constructs
   Dim varAtr As Variant
   Dim strNodeName As String
   Dim strNodeObozn As String
   Dim bolOk As Boolean
   Dim strSQL As String
   Dim colDetails As Collection
   Dim colNodes As New Collection
      
   'создаем коллекцию объектов узлов
   For Each objBlNode In colBlNode
      'определяем имя узла
      For Each varAtr In objBlNode.GetAttributes
         If LCase(varAtr.TagString) = "марка" Then
            strNodeName = varAtr.TextString
         End If
         If LCase(varAtr.TagString) = "обозначение" Then
            strNodeObozn = varAtr.TextString
         End If
      Next
      'создаем объект узла и заносим его в коллекцию объектов узлов
      On Error Resume Next
      Set objNode = colNodes.Item(strNodeName & strNodeObozn)
      On Error GoTo 0
      If objNode Is Nothing Then
         'если нет такого узла, создаем новый объект
         Set objNode = New clNode
         objNode.Name = strNodeName
         objNode.Obozn = strNodeObozn
         objNode.Kolvo = 1
         'для каждого узла получаем коллекцию деталей
         Set colDetails = Nothing
         Set colDetails = Functions.GetDetFromBase(strNodeName, strNodeObozn, sSer)
         'если найдены данные по узлу в базе, заносим объект в коллекцию
         If Not colDetails Is Nothing Then
            'записываем коллекцию деталей в объект узла
            If colDetails.Count <> 0 Then
               Set objNode.colDetails = colDetails
            End If
         Else
            'нет данных по узлу, заносим блок в коллекцию забракованных узлов
            colNodesBrack.Add objBlNode
         End If
         'заносим объект узла в коллекцию
         colNodes.Add objNode, objNode.Name & objNode.Obozn
      Else
         'если есть такой узел, прибавляем кол-во
'         'проверяем обозначение
'         If LCase(objNode.Obozn) <> LCase(strNodeObozn) Then
'            '(может быть ! ! !)в одном чертеже не должно быть двух узлов с одним именем но с разным обозначением!
'            'заносим в коллекцию двойных узлов
'            colNodesDublObozn.Add objBlNode
'         Else
            objNode.Kolvo = objNode.Kolvo + 1
'         End If
      End If
      Set objNode = Nothing
   Next
   
   Set GetColNodes = colNodes
      
End Function

Private Function MakeColDetails(colNodes As Collection) As Collection
   'составление общей коллекции деталей по в коллекции
   
   Dim objNode As clNode
   Dim objDetail As Constructs
   Dim objNodeDetail As Constructs
   
   Dim colDetails As New Collection
   
   For Each objNode In colNodes
      For Each objNodeDetail In objNode.colDetails
         On Error Resume Next
         Set objDetail = colDetails.Item(objNodeDetail.Name & objNodeDetail.Naimen)
         On Error GoTo 0
         If objDetail Is Nothing Then
            'если нет такой еще, добавляем в коллекцию
            objNodeDetail.Kolvo = objNodeDetail.Kolvo * objNode.Kolvo
            colDetails.Add objNodeDetail, objNodeDetail.Name & objNodeDetail.Naimen
         Else
            'если есть, добавляем кол-во
            objDetail.Kolvo = objNodeDetail.Kolvo * objNode.Kolvo + objDetail.Kolvo
         End If
         Set objDetail = Nothing
      Next
   Next
   
   Set MakeColDetails = colDetails
   
End Function

Private Function GetAttrMarka(oBlRef As AcadBlockReference) As String
   'возвращает атрибут марки из блока
   
   Dim vAttr As Variant
   Dim oAttrRef As AcadAttributeReference
   
   For Each vAttr In oBlRef.GetAttributes
      Set oAttrRef = vAttr
      If LCase(oAttrRef.Layer) = "att~marka" Then
         GetAttrMarka = oAttrRef.TextString
         Exit For
      End If
   Next
   If GetAttrMarka = "" Then
      GetAttrMarka = oBlRef.Name
   End If
   
End Function

Private Function TableForArchitectors()
  'Создание таблицы со списком наименований спецификаций для архитекторов
  
  'dPtInsertTable текущая точка вставленной таблицы
  
  'Вставить новый лист (условный, с одной таблицей) следом за последним листом
  'Выбрать все блоки штампов
  'Заполнить таблицу наименованиями из штампов
  
  Dim ent As AcadEntity
  Dim blStampa As AcadBlockReference
  Dim vAtr As Variant
  Dim iCount As Integer
  Dim sNaimen() As String
  
  iCount = -1
  For Each ent In objMS
    If TypeOf ent Is AcadBlockReference Then
      Set blStampa = ent
      If blStampa.Name = "Штамп1" Then
        For Each vAtr In blStampa.GetAttributes()
          If LCase(vAtr.TagString) = "наименование" Then
            iCount = iCount + 1
            ReDim Preserve sNaimen(iCount)
            sNaimen(iCount) = vAtr.TextString
            Exit For
          End If
        Next
      End If
    End If
  Next
  
  If iCount = -1 Then Exit Function
  
  dPtInsertTable(1) = dPtInsertTable(1) - 200
  
  Dim table As AcadTable
  Set table = objMS.AddTable(dPtInsertTable, iCount + 3, 2, 8, 15)
  
  table.StyleName = "Спецификация"
  table.RegenerateTableSuppressed = False
  
  table.SetColumnWidth 1, 120
  
  table.SetCellValue 0, 0, "Список листов спецификаций - " + FormaShtamp.TextBoxShifr
  table.SetRowHeight 0, 8
  
  table.SetCellValue 1, 0, "Лист"
  table.SetCellValue 1, 1, "Наименование"
  table.SetRowHeight 1, 15
  
  Dim i As Integer
  For i = 0 To iCount
    table.SetCellValue i + 2, 1, sNaimen(i)
    table.SetCellAlignment i + 2, 1, acMiddleLeft
    table.SetRowHeight i + 2, 8
  Next
  
  table.RegenerateTableSuppressed = True
  
End Function

Attribute VB_Name = "WinAPI"
Option Explicit

Private Declare Function GetComputerName Lib "kernel32" Alias "GetComputerNameA" (ByVal lpBuffer As String, nSize As Long) As Long
Private Declare Function GetUserName Lib "advapi32.dll" Alias "GetUserNameA" _
        (ByVal lpBuffer As String, nSize As Long) As Long

'функции получения имени компьютера и имени пользователя
'v_1.0.0 990630
Public Function ComputerName() As String
   Dim a As String * 40
   Dim nSize As Long
   nSize = 40
   Call GetComputerName(a, nSize)
   ComputerName = StrZ(a)
End Function
'v_1.0.0 990831
Public Function UserName() As String
Dim a As String * 40
Dim nSize As Long
nSize = 40
   Call GetUserName(a, nSize)
   UserName = StrZ(a)
End Function
'v_1.0.0 990630
Private Function StrZ(par As String) As String
Dim nSize As Long, i As Long, Rez As String
   nSize = Len(par)
   i = InStr(1, par, Chr(0)) - 1
   If i > nSize Then i = nSize
   If i < 0 Then i = nSize
   StrZ = Mid(par, 1, i)
End Function

Attribute VB_Name = "clDetail"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'данные по детале
   
   Dim strName As String
   Dim strUniqName As String
   Dim strNaimen As String
   Dim strObozn As String
   Dim dMassa As Double
   Dim intKolvo As Integer

'UniqName : уникальное имя детали (МС1Издел соед)
Public Property Get UniqName() As String
   UniqName = strUniqName
End Property
Public Property Let UniqName(ByVal vNewValue As String)
   strUniqName = vNewValue
End Property

'имя жетали (МС1)
Public Property Get Name() As String
   Name = strName
End Property
Public Property Let Name(ByVal vNewValue As String)
   strName = vNewValue
End Property

'наименовани : Изделие соед
Public Property Get Naimen() As String
   Naimen = strNaimen
End Property
Public Property Let Naimen(ByVal vNewValue As String)
   strNaimen = vNewValue
End Property

'обозначение : 5463-1-АС.У
Public Property Get Obozn() As String
   Obozn = strObozn
End Property
Public Property Let Obozn(ByVal vNewValue As String)
   strObozn = vNewValue
End Property

'масса - 0.16
Public Property Get Massa() As Double
   Massa = dMassa
End Property
Public Property Let Massa(ByVal vNewValue As Double)
   dMassa = vNewValue
End Property

'кол-во деталей
Public Property Get Kolvo() As Integer
   Kolvo = intKolvo
End Property
Public Property Let Kolvo(ByVal vNewValue As Integer)
   intKolvo = vNewValue
End Property

Attribute VB_Name = "clNode"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'данные по узлу

   Public colDetails As New Collection
   
   Dim strName As String
   Dim strObozn As String
   Dim intKolvo As Integer

'имя узла
Public Property Get Name() As String
   Name = strName
End Property
Public Property Let Name(ByVal vNewValue As String)
   strName = vNewValue
End Property

'обозначение - 5463-1-АС
Public Property Get Obozn() As String
   Obozn = strObozn
End Property
Public Property Let Obozn(ByVal vNewValue As String)
   strObozn = vNewValue
End Property

'кол-во блоков на чертеже
Public Property Get Kolvo() As Integer
   Kolvo = intKolvo
End Property
Public Property Let Kolvo(ByVal vNewValue As Integer)
   intKolvo = vNewValue
End Property

Attribute VB_Name = "clShifr"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
   
   Dim strShifr As String
   Dim strGIP As String
   Dim strClients As String
   Dim strAdress As String
   Dim strObjectName As String
   Dim strNachAKM As String
   Dim strNachSPD As String
   Dim strGlSpec As String
   Dim strBS As String
   Dim strPart As String

'шифр: например "3085-10"
Public Property Get Shifr() As String
   Shifr = strShifr
End Property
Public Property Let Shifr(ByVal strValue As String)
   strShifr = strValue
End Property

'(бс) - перечень б.с. - (А-К)
Public Property Get BS() As String
   BS = strBS
End Property
Public Property Let BS(ByVal strValue As String)
   strBS = strValue
End Property

'часть - АС
Public Property Get Part() As String
   Part = strPart
End Property
Public Property Let Part(ByVal strValue As String)
   strPart = strValue
End Property

'Фамилия И.О. ГИПа: Купряхин С.П.
Public Property Get GIP() As String
   GIP = strGIP
End Property
Public Property Let GIP(ByVal strValue As String)
   strGIP = strValue
End Property

'название фирмы заказчика : ООО"Кронверк-3"
Public Property Get Clients() As String
   Clients = strClients
End Property
Public Property Let Clients(ByVal strValue As String)
   strClients = strValue
End Property

'адресс объекта
Public Property Get Adress() As String
   Adress = strAdress
End Property
Public Property Let Adress(ByVal strValue As String)
   strAdress = strValue
End Property

'Наименование здания : Жилой дом №10
Public Property Get ObjectName() As String
   ObjectName = strObjectName
End Property
Public Property Let ObjectName(ByVal strValue As String)
   strObjectName = strValue
End Property

'начальник АКМ
Public Property Get NachAKM() As String
   NachAKM = strNachAKM
End Property
Public Property Let NachAKM(ByVal strValue As String)
   strNachAKM = strValue
End Property

'начальник СПД
Public Property Get NachSPD() As String
   NachSPD = strNachSPD
End Property
Public Property Let NachSPD(ByVal strValue As String)
   strNachSPD = strValue
End Property

'Фамилия главного специалиста
Public Property Get GlSpec() As String
   GlSpec = strGlSpec
End Property
Public Property Let GlSpec(ByVal strValue As String)
   strGlSpec = strValue
End Property
